module cliparser-extensions-v11 {
  // Generated by yanger -t ncs
  tailf:mount-id "cisco-ios-cli-6.106:cisco-ios-cli-6.106";
  tailf:ncs-device-type "cli-ned";

  namespace "http://tail-f.com/ned/cliparser_v11";
  prefix cli;

  import tailf-common {
    prefix tailf;
  }
  import tailf-ncs {
    prefix ncs;
  }

  extension ned-diff-stay-before {
    argument value;
    cli:direction "to-device";
    cli:state "post-match|parent-context-deleted";
    cli:java-callback-method "com.tailf.packages.ned.nedcom.NedDiffCliExtensions.stayBefore";
  }

  extension ned-diff-stay-after {
    argument value;
    cli:direction "to-device";
    cli:state "post-match|parent-context-deleted";
    cli:java-callback-method "com.tailf.packages.ned.nedcom.NedDiffCliExtensions.stayAfter";
  }

  extension ned-diff-move-before {
    argument value;
    cli:direction "to-device";
    cli:state "post-match|parent-context-deleted";
    cli:java-callback-method "com.tailf.packages.ned.nedcom.NedDiffCliExtensions.moveBefore";
  }

  extension ned-diff-move-after {
    argument value;
    cli:direction "to-device";
    cli:state "post-match|parent-context-deleted";
    cli:java-callback-method "com.tailf.packages.ned.nedcom.NedDiffCliExtensions.moveAfter";
  }

  extension ned-diff-move-last {
    cli:direction "to-device";
    cli:state "post-match|parent-context-deleted";
    cli:java-callback-method "com.tailf.packages.ned.nedcom.NedDiffCliExtensions.moveLast";
  }

  extension ned-diff-move-first {
    cli:direction "to-device";
    cli:state "post-match|parent-context-deleted";
    cli:java-callback-method "com.tailf.packages.ned.nedcom.NedDiffCliExtensions.moveFirst";
  }

  extension ned-diff-add {
    cli:direction "to-device";
    cli:state "post-match|parent-context-deleted";
    cli:java-callback-method "com.tailf.packages.ned.nedcom.NedDiffCliExtensions.add";
  }

  extension multi-line-banner {
    cli:direction "both";
    cli:state "multi-line";
    cli:java-callback-method "com.tailf.packages.ned.nedcom.NedComCliExtensions.multiLineBanner";
  }

  extension custom-delete {
    argument value;
    cli:direction "to-device";
    cli:state "post-match";
    cli:java-callback-method "com.tailf.packages.ned.nedcom.NedComCliExtensions.deleteWith";
  }

  extension trim-delete-if-match {
    argument value;
    cli:direction "to-device";
    cli:state "post-match";
    cli:java-callback-method "com.tailf.packages.ned.nedcom.NedComCliExtensions.deleteWith";
  }

  extension trim-delete {
    cli:direction "to-device";
    cli:state "post-match";
    cli:java-callback-method "com.tailf.packages.ned.nedcom.NedComCliExtensions.deleteWith";
  }

  extension delete-with-default {
    cli:direction "to-device";
    cli:state "post-match";
    cli:java-callback-method "com.tailf.packages.ned.nedcom.NedComCliExtensions.deleteWith";
  }

  extension secret {
    cli:direction "both";
    cli:state "post-match";
    cli:java-callback-method "com.tailf.packages.ned.nedcom.NedComCliExtensions.secret";
  }

  extension split-chunk {
    cli:direction "to-device";
    cli:state "post-match";
    cli:java-callback-method "com.tailf.packages.ned.nedcom.NedComCliExtensions.splitChunk";
    argument value;
  }

  extension globally-unique-value {
    cli:direction "to-device";
    cli:state "post-match|parent-context-deleted";
    cli:java-callback-method "com.tailf.packages.ned.nedcom.NedComCliExtensions.globallyUniqueValue";
    argument value;
  }

  extension shutdown-before-edit {
    cli:direction "to-device";
    cli:state "post-match";
    cli:java-callback-method "com.tailf.packages.ned.nedcom.NedComCliExtensions.shutdownBeforeEdit";
    argument value;
  }

  extension context-value-set-default {
    cli:direction "from-device";
    cli:state "last-exit-context";
    cli:java-callback-method "com.tailf.packages.ned.nedcom.NedComCliExtensions.contextValueInject";
    argument value;
  }

  extension context-value-inject {
    cli:direction "from-device";
    cli:state "enter-context";
    cli:java-callback-method "com.tailf.packages.ned.nedcom.NedComCliExtensions.contextValueInject";
    argument value;
  }

  extension context-shutdown-handler {
    cli:direction "to-device";
    cli:state "first-enter-context|last-exit-context";
    cli:java-callback-method "com.tailf.packages.ned.nedcom.NedComCliExtensions.contextShutdownHandler";
  }

  extension forced-relaxed-parse-in-path {
    cli:builtin "true";
    argument value;
  }

  extension forced-when-eval-in-path {
    cli:builtin "true";
    argument value;
  }

  extension compact-need-when-eval {
    cli:builtin "true";
  }

  extension when-target-set {
    cli:builtin "true";
    cli:state "none";
  }

  extension when-target-delete {
    cli:builtin "true";
    cli:state "none";
  }

  extension diff-set-after {
    cli:builtin "true";
    cli:state "none";
    argument value;
  }

  extension diff-set-before {
    cli:builtin "true";
    cli:state "none";
    argument value;
  }

  extension diff-delete-after {
    cli:builtin "true";
    cli:state "none";
    argument value;
  }

  extension diff-delete-before {
    cli:builtin "true";
    cli:state "none";
    argument value;
  }

  extension diff-explicit-choice {
    cli:builtin "true";
    cli:state "none";
    argument value;
  }

  extension diff-dependency {
    cli:builtin "true";
    cli:state "none";
    argument value;
  }

  extension parse-match-prefix {
    cli:builtin "true";
  }

  extension parse-disallow-type {
    cli:builtin "true";
    argument value;
  }

  extension parse-no-auto-match {
    cli:builtin "true";
  }

  extension parse-alt-regex {
    cli:builtin "true";
    argument value;
  }

  extension parse-alt-name {
    cli:builtin "true";
    argument value;
  }

  extension parse-inline-when {
    cli:builtin "true";
  }

  extension parse-global-when {
    cli:builtin "true";
  }

  extension parse-relaxed-syntax {
    cli:builtin "true";
  }

  extension parse-compact-syntax {
    cli:builtin "true";
  }

  extension java-callback-method {
    cli:builtin "true";
    argument value;
  }

  extension module-meta-data {
    cli:builtin "true";
  }

  extension callback {
    cli:builtin "true";
    argument value;
  }

  extension json-arguments {
    cli:builtin "true";
    argument value;
  }

  extension arguments {
    cli:builtin "true";
    argument value;
  }

  extension state {
    cli:builtin "true";
    argument value;
  }

  extension direction {
    cli:builtin "true";
    argument value;
  }

  extension builtin {
    argument value;
    cli:builtin "true";
  }
}
