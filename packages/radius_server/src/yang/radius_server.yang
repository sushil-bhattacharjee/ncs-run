module radius_server {
  namespace "http://com/example/radius_server";
  prefix radius_server;

  import ietf-inet-types {
    prefix inet;
  }
  import tailf-ncs {
    prefix ncs;
  }

  augment /ncs:services {
  list radius_server {
    key Location;

    leaf Location {
      type enumeration {
        enum "Sydney";
        enum "Brisbane";
        enum "Perth";
        enum "Darwin";
        enum "Adelaide";
      }
    }

    leaf name {
      type string;
    }

    // may replace this with other ways of refering to the devices.
    leaf-list device {
      type leafref {
        path "/ncs:devices/ncs:device/ncs:name";
      }
    }

    // replace with your own stuff here
    leaf the-ipv4-address {
      type inet:ipv4-address;
    }
  }
  } // augment /ncs:services {
}
