module tailf-ned-cisco-ios {
  // Generated by yanger -t ncs
  tailf:mount-id "cisco-ios-cli-3.0:cisco-ios-cli-3.0";
  tailf:ncs-device-type "cli-ned";

  namespace "urn:ios";
  prefix ios;

  import tailf-common {
    prefix tailf;
  }
  import ietf-inet-types {
    prefix inet;
  }
  import ietf-yang-types {
    prefix yang;
  }
  import tailf-ncs {
    prefix ncs;
  }

  revision 2014-02-12 {
    description
      "Fixed show live-status for interfaces.";
  }
  revision 2014-02-10 {
    description
      "[ip] vrf forwarding fix on interfaces.
      ";
  }
  revision 2014-02-06 {
    description
      "Fixed interface 'no ip address' bug
       Preliminary IOS XE support work
       Added 'interface Virtual-Template *'
       Added 'interface * / peer default ip' support'
       Expanded 'interface * / ppp' support'
       Merged interface encapsulation config (API change)
       Merged all fixes/adds in confd-4.3 ios-xe between r59179 and r65905.
      ";
  }
  revision 2014-01-30 {
    description
      "Merged from confd-5.0
       Expanded 'ip nat'";
  }
  revision 2014-01-28 {
    description
      "Fixed bugs in 'ip route'. API changes to list due to variable
       number of keys.";
  }
  revision 2013-12-09 {
    description
      "police and policer work";
  }
  revision 2013-11-25 {
    description
      "API-cleaning for Juniper and bugfixes
       Made cir,bc and be keywords mandatory in policy-map/class police";
  }
  revision 2013-11-12 {
    description
      "Rewrote police-map/class police command to support more combos";
  }
  revision 2013-10-14 {
    description
      "Merged all yang files to one file.";
  }
  revision 2013-08-15 {
    description
      "Added switchport commands
       Added spanning-tree top level commands
       Added a number of SNMP traps
       Added support for OSPFv3
       Added support for IPv6 prefix-lists
      ";
  }
  revision 2013-08-08 {
    description
      "Added support for Cisco 7600 constructs.";
  }
  revision 2013-06-25 {
    description
      "Renamed YANG module, submodule and namespace.";
  }
  revision 2013-04-18 {
    description
      "Restructuring using new file ios-common0.yang and
       augment(s) in order to fix order dependencies.

       Added model constructs for Cisco 2800.";
  }

  typedef ncs_compliance_template_percentage-type {
    type string;
  }

  typedef ncs_compliance_template_ipv4-prefix {
    type string;
  }

  typedef ncs_compliance_template_ipv6-prefix {
    type string;
  }

  typedef ncs_compliance_template_host-type {
    type string;
  }

  typedef ncs_compliance_template_rd-type {
    type string;
  }

  typedef ncs_compliance_template_vpn-id-type {
    type string;
  }

  typedef ncs_compliance_template_asn-ip-type {
    type string;
  }

  typedef ncs_compliance_template_hhmm-type {
    type string;
  }

  typedef ncs_compliance_template_weekday-type {
    type string;
  }

  typedef ncs_compliance_template_month-type {
    type string;
  }

  typedef ncs_compliance_template_std-acl-type {
    type string;
  }

  typedef ncs_compliance_template_ext-acl-type {
    type string;
  }

  typedef ncs_compliance_template_exp-acl-type {
    type string;
  }

  typedef ncs_compliance_template_mdt-data-list-type {
    type string;
  }

  typedef ncs_compliance_template_ldp-discovery-address-type {
    type string;
  }

  typedef ncs_compliance_template_mst-cost-type {
    type string;
  }

  typedef ncs_compliance_template_spanning-tree-cost-type {
    type string;
  }

  typedef ncs_compliance_template_dscp-type {
    type string;
  }

  typedef ncs_compliance_template_precedence-type {
    type string;
  }

  typedef ncs_compliance_template_precedence-type2 {
    type string;
  }

  typedef ncs_compliance_template_cos_value-type {
    type string;
  }

  typedef ncs_compliance_template_qos_value-type {
    type string;
  }

  typedef ncs_compliance_template_exp_value-type {
    type string;
  }

  typedef ncs_compliance_template_prec_value-type {
    type string;
  }

  typedef ncs_compliance_template_access-list-standard-id-type {
    type string;
  }

  typedef ncs_compliance_template_default-access-list-standard-id-type {
    type string;
  }

  typedef ncs_compliance_template_access-list-in-out-type {
    type string;
  }

  typedef ncs_compliance_template_redist-ospf-external-type {
    type string;
  }

  typedef ncs_compliance_template_class-name-type {
    type string;
  }

  typedef ncs_compliance_template_access-list-type {
    type string;
  }

  typedef ncs_compliance_template_bgp-distribute-list-type {
    type string;
  }

  typedef ncs_compliance_template_bgp-distribute-list-type2 {
    type string;
  }

  typedef ncs_compliance_template_ospf-area-type {
    type string;
  }

  typedef ncs_compliance_template_ospf-metric-type {
    type string;
  }

  typedef ncs_compliance_template_limit-dc-non-dc-type {
    type string;
  }

  typedef ncs_compliance_template_default-access-list-id-type {
    type string;
  }

  typedef ncs_compliance_template_access-list-id-type {
    type string;
  }

  typedef ncs_compliance_template_default-offset-list-id-type {
    type string;
  }

  typedef ncs_compliance_template_offset-list-id-type {
    type string;
  }

  typedef ncs_compliance_template_offset-list-in-out-type {
    type string;
  }

  typedef ncs_compliance_template_isis-net {
    type string;
  }

  typedef ncs_compliance_template_isis-level-type {
    type string;
  }

  typedef ncs_compliance_template_isis-routes-level-type {
    type string;
  }

  typedef ncs_compliance_template_authentication-level-type {
    type string;
  }

  typedef ncs_compliance_template_logging-level-type {
    type string;
  }

  typedef ncs_compliance_template_operator-type {
    type string;
  }

  typedef ncs_compliance_template_police-packets-bytes-type {
    type string;
  }

  typedef ncs_compliance_template_police-pps-bps-type {
    type string;
  }

  typedef ncs_compliance_template_police-bps-type {
    type string;
  }

  typedef ncs_compliance_template_police-burst-type {
    type string;
  }

  typedef ncs_template_percentage-type {
    type string;
  }

  typedef ncs_template_ipv4-prefix {
    type string;
  }

  typedef ncs_template_ipv6-prefix {
    type string;
  }

  typedef ncs_template_host-type {
    type string;
  }

  typedef ncs_template_rd-type {
    type string;
  }

  typedef ncs_template_vpn-id-type {
    type string;
  }

  typedef ncs_template_asn-ip-type {
    type string;
  }

  typedef ncs_template_hhmm-type {
    type string;
  }

  typedef ncs_template_weekday-type {
    type string;
  }

  typedef ncs_template_month-type {
    type string;
  }

  typedef ncs_template_std-acl-type {
    type string;
  }

  typedef ncs_template_ext-acl-type {
    type string;
  }

  typedef ncs_template_exp-acl-type {
    type string;
  }

  typedef ncs_template_mdt-data-list-type {
    type string;
  }

  typedef ncs_template_ldp-discovery-address-type {
    type string;
  }

  typedef ncs_template_mst-cost-type {
    type string;
  }

  typedef ncs_template_spanning-tree-cost-type {
    type string;
  }

  typedef ncs_template_dscp-type {
    type string;
  }

  typedef ncs_template_precedence-type {
    type string;
  }

  typedef ncs_template_precedence-type2 {
    type string;
  }

  typedef ncs_template_cos_value-type {
    type string;
  }

  typedef ncs_template_qos_value-type {
    type string;
  }

  typedef ncs_template_exp_value-type {
    type string;
  }

  typedef ncs_template_prec_value-type {
    type string;
  }

  typedef ncs_template_access-list-standard-id-type {
    type string;
  }

  typedef ncs_template_default-access-list-standard-id-type {
    type string;
  }

  typedef ncs_template_access-list-in-out-type {
    type string;
  }

  typedef ncs_template_redist-ospf-external-type {
    type string;
  }

  typedef ncs_template_class-name-type {
    type string;
  }

  typedef ncs_template_access-list-type {
    type string;
  }

  typedef ncs_template_bgp-distribute-list-type {
    type string;
  }

  typedef ncs_template_bgp-distribute-list-type2 {
    type string;
  }

  typedef ncs_template_ospf-area-type {
    type string;
  }

  typedef ncs_template_ospf-metric-type {
    type string;
  }

  typedef ncs_template_limit-dc-non-dc-type {
    type string;
  }

  typedef ncs_template_default-access-list-id-type {
    type string;
  }

  typedef ncs_template_access-list-id-type {
    type string;
  }

  typedef ncs_template_default-offset-list-id-type {
    type string;
  }

  typedef ncs_template_offset-list-id-type {
    type string;
  }

  typedef ncs_template_offset-list-in-out-type {
    type string;
  }

  typedef ncs_template_isis-net {
    type string;
  }

  typedef ncs_template_isis-level-type {
    type string;
  }

  typedef ncs_template_isis-routes-level-type {
    type string;
  }

  typedef ncs_template_authentication-level-type {
    type string;
  }

  typedef ncs_template_logging-level-type {
    type string;
  }

  typedef ncs_template_operator-type {
    type string;
  }

  typedef ncs_template_police-packets-bytes-type {
    type string;
  }

  typedef ncs_template_police-pps-bps-type {
    type string;
  }

  typedef ncs_template_police-bps-type {
    type string;
  }

  typedef ncs_template_police-burst-type {
    type string;
  }

  typedef ncs_rpc_notif_percentage-type {
    type uint8 {
      tailf:info
        "<1-100>;;Percentage";
      range "1..100";
    }
  }

  typedef ncs_rpc_notif_ipv4-prefix {
    type string {
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
  }

  typedef ncs_rpc_notif_ipv6-prefix {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(/(([0-9])|([0-9]{2})|(1[0-1][0-9])|(12[0-8])))';
      pattern '(([^:]+:){6}(([^:]+:[^:]+)|(.*\..*)))|((([^:]+:)*[^:]+)?::(([^:]+:)*[^:]+)?)(/.+)';
    }
  }

  typedef ncs_rpc_notif_host-type {
    type union {
      type inet:ip-address {
        tailf:info
          "";
      }
      type inet:domain-name {
        tailf:info
          "";
      }
    }
  }

  typedef ncs_rpc_notif_rd-type {
    type string {
      tailf:info
        "ASN:nn or IP-address:nn;;VPN Route Distinguisher";
      pattern '(\d*(.\d*)*)?:(\d*(.\d*)*)?';
    }
  }

  typedef ncs_rpc_notif_vpn-id-type {
    type string {
      tailf:info
        "OUI:VPN-Index;;, format (hex) <3 bytes OUI:4 bytes VPN_Index>";
      pattern '[0-9a-fA-F][0-9a-fA-F]?[0-9a-fA-F]?:[0-9a-fA-F][0-9a-fA-F]?[0-9a-fA-F]?[0-9a-fA-F]?';
    }
  }

  typedef ncs_rpc_notif_asn-ip-type {
    type string {
      pattern '(([0-9]+)|((([0-9]|[1-9][0-9]|1[0-9][0-9]|2[0-4][0-9]|25[0-5])\.){3}([0-9]|[1-9][0-9]|1[0-9][0-9]|2[0-4][0-9]|25[0-5]))):[0-9]+';
      tailf:info
        "ASN:nn or IP-address:nn";
    }
  }

  typedef ncs_rpc_notif_hhmm-type {
    type string {
      pattern '([0-1]?[0-9]|2[0-4]):([0-5][0-9])(:[0-5][0-9])?';
    }
  }

  typedef ncs_rpc_notif_weekday-type {
    type enumeration {
      enum "Mon";
      enum "Tue";
      enum "Wed";
      enum "Thu";
      enum "Fri";
      enum "Sat";
      enum "Sun";
    }
  }

  typedef ncs_rpc_notif_month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef ncs_rpc_notif_std-acl-type {
    type union {
      type uint16 {
        tailf:info
          "<1-99>;;Standard IP access-list number";
        range "1..99";
      }
      type uint16 {
        tailf:info
          "<1300-1999>;;Standard IP access-list number (expanded range)";
        range "1300..1999";
      }
      type string {
        tailf:info
          "WORD;;Access-list name";
        pattern '[a-zA-Z].*';
      }
    }
  }

  typedef ncs_rpc_notif_ext-acl-type {
    type union {
      type uint16 {
        tailf:info
          "<100-199>;;Access list number";
        range "100..199";
      }
      type uint16 {
        tailf:info
          "<2000-2699>;;Access list number (expanded range)";
        range "2000..2699";
      }
      type string {
        tailf:info
          "WORD;;IP Named Extended Access list";
        pattern '[a-zA-Z].*';
      }
    }
  }

  typedef ncs_rpc_notif_exp-acl-type {
    type union {
      type uint16 {
        tailf:info
          "<1-199>;;IP access list (standard or extended)";
        range "1..199";
      }
      type uint16 {
        tailf:info
          "<1300-2699>;;IP expanded access list (standard or extended)";
        range "1300..2699";
      }
      type string {
        tailf:info
          "WORD;;Access-list name";
        pattern '[a-zA-Z].*';
      }
    }
  }

  typedef ncs_rpc_notif_mdt-data-list-type {
    type union {
      type uint16 {
        tailf:info
          "<100-199>;;Access-list number";
        range "100..199";
      }
      type uint16 {
        tailf:info
          "<2000-2699>;;Access list number (expanded range)";
        range "2000..2699";
      }
      type string {
        tailf:info
          "WORD;;IP Named Extended Access list";
        pattern '[a-fA-F].*';
      }
    }
  }

  typedef ncs_rpc_notif_ldp-discovery-address-type {
    type union {
      type enumeration {
        enum "interface" {
          tailf:code-name "ldp_interface";
          tailf:info
            "Use interface address for LDP transport address";
        }
      }
      type inet:ipv4-address {
        tailf:info
          "A.B.C.D;;IP address to use for LDP transport address";
      }
    }
  }

  typedef ncs_rpc_notif_mst-cost-type {
    type union {
      type uint32 {
        tailf:info
          "<1-200000000>;;Port path cost";
        range "1..200000000";
      }
      type enumeration {
        enum "auto" {
          tailf:code-name "mst_cost_type_auto";
          tailf:info
            "Determine cost based on media speed of this interface";
        }
      }
    }
  }

  typedef ncs_rpc_notif_spanning-tree-cost-type {
    type union {
      type uint32 {
        tailf:info
          "<1-200000000>;;Port path cost";
        range "1..200000000";
      }
      type enumeration {
        enum "auto" {
          tailf:code-name "spanning-tree-cost-type-auto";
          tailf:info
            "Determine cost based on media speed of this interface";
        }
      }
    }
  }

  typedef ncs_rpc_notif_dscp-type {
    type union {
      type uint8 {
        tailf:info
          "<0-63>;;Differentiated services codepoint value";
        range "0..63";
      }
      type enumeration {
        enum "af11" {
          tailf:info
            "Match packets with AF11 dscp (001010)";
        }
        enum "af12" {
          tailf:info
            "Match packets with AF12 dscp (001100)";
        }
        enum "af13" {
          tailf:info
            "Match packets with AF13 dscp (001110)";
        }
        enum "af21" {
          tailf:info
            "Match packets with AF21 dscp (010010)";
        }
        enum "af22" {
          tailf:info
            "Match packets with AF22 dscp (010100)";
        }
        enum "af23" {
          tailf:info
            "Match packets with AF23 dscp (010110)";
        }
        enum "af31" {
          tailf:info
            "Match packets with AF31 dscp (011010)";
        }
        enum "af32" {
          tailf:info
            "Match packets with AF32 dscp (011100)";
        }
        enum "af33" {
          tailf:info
            "Match packets with AF33 dscp (011110)";
        }
        enum "af41" {
          tailf:info
            "Match packets with AF41 dscp (100010)";
        }
        enum "af42" {
          tailf:info
            "Match packets with AF42 dscp (100100)";
        }
        enum "af43" {
          tailf:info
            "Match packets with AF43 dscp (100110)";
        }
        enum "cs1" {
          tailf:info
            "Match packets with CS1(precedence 1) dscp (001000)";
        }
        enum "cs2" {
          tailf:info
            "Match packets with CS2(precedence 2) dscp (010000)";
        }
        enum "cs3" {
          tailf:info
            "Match packets with CS3(precedence 3) dscp (011000)";
        }
        enum "cs4" {
          tailf:info
            "Match packets with CS4(precedence 4) dscp (100000)";
        }
        enum "cs5" {
          tailf:info
            "Match packets with CS5(precedence 5) dscp (101000)";
        }
        enum "cs6" {
          tailf:info
            "Match packets with CS6(precedence 6) dscp (110000)";
        }
        enum "cs7" {
          tailf:info
            "Match packets with CS7(precedence 7) dscp (111000)";
        }
        enum "default" {
          tailf:code-name "dscp_default";
          tailf:info
            "Match packets with default dscp (000000)";
        }
        enum "dscp" {
          tailf:info
            "Set packet dscp from dscp";
        }
        enum "ef" {
          tailf:info
            "Match packets with EF dscp (101110)";
        }
        enum "precedence" {
          tailf:info
            "Set packet dscp from precedence";
        }
      }
    }
  }

  typedef ncs_rpc_notif_precedence-type {
    type union {
      type uint8 {
        tailf:info
          "<0-7>;;Precedence value";
        range "0..7";
      }
      type enumeration {
        enum "critical" {
          tailf:info
            "Set packets with critical precedence (5)";
        }
        enum "flash" {
          tailf:info
            "Set packets with flash precedence (3)";
        }
        enum "flash-override" {
          tailf:info
            "Set packets with flash override precedence (4)";
        }
        enum "immediate" {
          tailf:info
            "Set packets with immediate precedence (2)";
        }
        enum "internet" {
          tailf:code-name "prec_internet";
          tailf:info
            "Set packets with internetwork control precedence (6)";
        }
        enum "network" {
          tailf:info
            "Set packets with network control precedence (7)";
        }
        enum "priority" {
          tailf:code-name "prec_priority";
          tailf:info
            "Set packets with priority precedence (1)";
        }
        enum "routine" {
          tailf:info
            "Set packets with routine precedence (0)";
        }
      }
    }
  }

  typedef ncs_rpc_notif_precedence-type2 {
    type union {
      type uint8 {
        tailf:info
          "<0-7>;;IP precedence";
        range "0..7";
      }
      type enumeration {
        enum "rsvp" {
          tailf:code-name "prec_rsvp";
          tailf:info
            "rsvp traffic";
        }
      }
    }
  }

  typedef ncs_rpc_notif_cos_value-type {
    type union {
      type uint8 {
        tailf:info
          "<0-7>;;new cos value";
        range "0..7";
      }
      type enumeration {
        enum "cos" {
          tailf:info
            "Set packet cos from cos";
        }
        enum "dscp" {
          tailf:info
            "Set packet cos from dscp";
        }
        enum "exp" {
          tailf:info
            "Set packet cos from exp";
        }
        enum "precedence" {
          tailf:info
            "Set packet cos from precedence";
        }
      }
    }
  }

  typedef ncs_rpc_notif_qos_value-type {
    type union {
      type uint8 {
        tailf:info
          "<0-99>;;new qos-group";
        range "0..99";
      }
      type enumeration {
        enum "cos" {
          tailf:info
            "Set packet qos from cos";
        }
        enum "dscp" {
          tailf:info
            "Set packet qos from dscp";
        }
        enum "exp" {
          tailf:info
            "Set packet qos from exp";
        }
        enum "precedence" {
          tailf:info
            "Set packet qos from precedence";
        }
      }
    }
  }

  typedef ncs_rpc_notif_exp_value-type {
    type union {
      type uint8 {
        tailf:info
          "<0-7>;;new exp";
        range "0..7";
      }
      type enumeration {
        enum "cos" {
          tailf:info
            "Set packet exp from cos";
        }
        enum "dscp" {
          tailf:info
            "Set packet exp from dscp";
        }
        enum "exp" {
          tailf:info
            "Set packet exp from exp";
        }
        enum "precedence" {
          tailf:info
            "Set packet exp from precedence";
        }
      }
    }
  }

  typedef ncs_rpc_notif_prec_value-type {
    type union {
      type uint8 {
        tailf:info
          "<0-7>;;new precedence";
        range "0..7";
      }
      type enumeration {
        enum "cos" {
          tailf:info
            "Set packet precedence from cos";
        }
        enum "dscp" {
          tailf:info
            "Set packet precedence from dscp";
        }
        enum "exp" {
          tailf:info
            "Set packet precedence from exp";
        }
        enum "precedence" {
          tailf:info
            "Set packet precedence from precedence";
        }
      }
    }
  }

  typedef ncs_rpc_notif_access-list-standard-id-type {
    type union {
      type ncs_rpc_notif_default-access-list-standard-id-type;
      type string {
        tailf:info
          "WORD;;Standard access-list name";
      }
    }
  }

  typedef ncs_rpc_notif_default-access-list-standard-id-type {
    type union {
      type uint8 {
        tailf:info
          "<1-99>;;IP Standard access list number";
        range "1..99";
      }
      type uint16 {
        tailf:info
          "<1300-1999>;;IP Standard expanded access list number";
        range "1300..1999";
      }
    }
  }

  typedef ncs_rpc_notif_access-list-in-out-type {
    type enumeration {
      enum "in" {
        tailf:info
          "Filter incoming routing updates";
      }
      enum "out" {
        tailf:info
          "Filter outgoing routing updates";
      }
    }
  }

  typedef ncs_rpc_notif_redist-ospf-external-type {
    type enumeration {
      enum "1" {
        tailf:info
          "Redistribute external type 1 routes";
      }
      enum "2" {
        tailf:info
          "Redistribute external type 2 routes";
      }
    }
  }

  typedef ncs_rpc_notif_class-name-type {
    type union {
      type string {
        tailf:info
          "WORD;;class-map name";
      }
      type enumeration {
        enum "class-default" {
          tailf:info
            "System default class matching otherwise unclassified packet";
        }
      }
    }
  }

  typedef ncs_rpc_notif_access-list-type {
    type union {
      type uint16 {
        range "1..199";
        tailf:info
          "<1-199>;;Access list";
      }
      type uint16 {
        range "1300..2699";
        tailf:info
          "<1300-2699>;;Access list (expanded range)";
      }
    }
  }

  typedef ncs_rpc_notif_bgp-distribute-list-type {
    type union {
      type uint16 {
        range "100..199";
        tailf:info
          "<100-199>;;IP access-list number";
      }
      type uint16 {
        range "2000..2699";
        tailf:info
          "<2000-2699>;;IP expanded access list number";
      }
      type string {
        tailf:info
          "WORD;;Access-list name";
        pattern '[a-zA-Z].*';
      }
    }
  }

  typedef ncs_rpc_notif_bgp-distribute-list-type2 {
    type union {
      type uint16 {
        range "1..199";
        tailf:info
          "<1-199>;;IP access list number";
      }
      type uint16 {
        range "1300..2699";
        tailf:info
          "<1300-2699>;;IP access list number (expanded range)";
      }
      type string {
        tailf:info
          "WORD;;Access-list name";
        pattern '[a-zA-Z].*';
      }
    }
  }

  typedef ncs_rpc_notif_ospf-area-type {
    type union {
      type uint32 {
        range "0 .. 4294967295";
        tailf:info
          "<0-4294967295>;;OSPF area ID as a decimal value";
      }
      type inet:ipv4-address {
        tailf:info
          "A.B.C.D;;OSPF area ID in IP address format";
      }
    }
  }

  typedef ncs_rpc_notif_ospf-metric-type {
    type uint32 {
      range "1 .. 2";
      tailf:info
        "<1-2>;;OSPF Link State type";
    }
  }

  typedef ncs_rpc_notif_limit-dc-non-dc-type {
    type union {
      type uint32 {
        range "1 .. 255";
        tailf:info
          "<1-255>;;The maximum number of retransmissions";
      }
      type enumeration {
        enum "disable" {
          tailf:info
            "Disable the feature";
        }
      }
    }
  }

  typedef ncs_rpc_notif_default-access-list-id-type {
    type union {
      type uint32 {
        range "1 .. 199";
        tailf:info
          "<1-199>;;IP access list number";
      }
      type uint32 {
        range "1300 .. 2699";
        tailf:info
          "<1300-2699>;;IP expanded access list number";
      }
    }
  }

  typedef ncs_rpc_notif_access-list-id-type {
    type union {
      type ncs_rpc_notif_default-access-list-id-type;
      type string {
        tailf:info
          "WORD;;Access-list name";
        pattern '[a-zA-Z].*';
      }
    }
  }

  typedef ncs_rpc_notif_default-offset-list-id-type {
    type union {
      type uint32 {
        range "0 .. 99";
        tailf:info
          "<0-99>;;Access list of networks to apply offset (0 selects all networks)";
      }
      type uint32 {
        range "1300 .. 1999";
        tailf:info
          "<1300-1999>;;Access list of networks to apply offset (expanded range)";
      }
    }
  }

  typedef ncs_rpc_notif_offset-list-id-type {
    type union {
      type ncs_rpc_notif_default-offset-list-id-type;
      type string {
        tailf:info
          "WORD;;Access-list name";
        pattern '[a-zA-Z].*';
      }
    }
  }

  typedef ncs_rpc_notif_offset-list-in-out-type {
    type enumeration {
      enum "in" {
        tailf:info
          "Perform offset on incoming updates";
      }
      enum "out" {
        tailf:info
          "Perform offset on outgoing updates";
      }
    }
  }

  typedef ncs_rpc_notif_isis-net {
    tailf:info
      "XX.XXXX. ... .XXX.XX;;Network entity title (NET)";
    type string {
      pattern '(([0-9a-fA-F]{2}\.[0-9a-fA-F]{4})|[0-9a-fA-F]{4})\.([0-9a-fA-F]{4}\.){3,10}00';
    }
  }

  typedef ncs_rpc_notif_isis-level-type {
    type enumeration {
      enum "level-1" {
        tailf:info
          "Level-1 only";
      }
      enum "level-1-2" {
        tailf:info
          "Level-1-2";
      }
      enum "level-2" {
        tailf:info
          "Level-2 only";
      }
    }
  }

  typedef ncs_rpc_notif_isis-routes-level-type {
    type enumeration {
      enum "level-1" {
        tailf:info
          "IS-IS level-1 routes only";
      }
      enum "level-1-2" {
        tailf:info
          "IS-IS level-1 and level-2 routes";
      }
      enum "level-2" {
        tailf:info
          "IS-IS level-2 routes only";
      }
    }
  }

  typedef ncs_rpc_notif_authentication-level-type {
    type enumeration {
      enum "level-1" {
        tailf:info
          "ISIS authentication for level-1";
      }
      enum "level-2" {
        tailf:info
          "ISIS authentication for level-2";
      }
    }
  }

  typedef ncs_rpc_notif_logging-level-type {
    type union {
      type uint16 {
        tailf:info
          "<0-7>;;Logging severity level";
        range "0..7";
      }
      type enumeration {
        enum "alerts" {
          tailf:info
            "Immediate action needed (severity=1)";
        }
        enum "critical" {
          tailf:info
            "Critical conditions (severity=2)";
        }
        enum "debugging" {
          tailf:info
            "Debugging messages (severity=7)";
        }
        enum "emergencies" {
          tailf:info
            "System is unusable (severity=0)";
        }
        enum "errors" {
          tailf:info
            "Error conditions (severity=3)";
        }
        enum "informational" {
          tailf:info
            "Informational messages (severity=6)";
        }
        enum "notifications" {
          tailf:info
            "Normal but significant conditions (severity=5)";
        }
        enum "warnings" {
          tailf:info
            "Warning conditions (severity=4)";
        }
      }
    }
  }

  typedef ncs_rpc_notif_operator-type {
    type enumeration {
      enum "eq" {
        tailf:info
          "Equal to";
      }
      enum "ge" {
        tailf:info
          "Greater than or equal to";
      }
      enum "gt" {
        tailf:info
          "Greater than";
      }
      enum "le" {
        tailf:info
          "Less than or equal to";
      }
      enum "lt" {
        tailf:info
          "Less than";
      }
      enum "ne" {
        tailf:info
          "Not equal to";
      }
    }
  }

  typedef ncs_rpc_notif_police-packets-bytes-type {
    type enumeration {
      enum "packets" {
        tailf:info
          "Treat 'burst' value as packets";
      }
      enum "bytes" {
        tailf:info
          "Treat 'burst' value as bytes";
      }
    }
  }

  typedef ncs_rpc_notif_police-pps-bps-type {
    type enumeration {
      enum "pps" {
        tailf:info
          "pps  Treat 'rate' value in packets-per-second";
      }
      enum "bps" {
        tailf:info
          "pps  Treat 'rate' value in bytes-per-second";
      }
    }
  }

  typedef ncs_rpc_notif_police-bps-type {
    type uint64 {
      tailf:info
        "<8000-64000000000>;;Bits per second";
      range "8000..64000000000";
    }
  }

  typedef ncs_rpc_notif_police-burst-type {
    type uint32 {
      tailf:info
        "<1000-512000000>;;Burst bytes";
      range "1000..512000000";
    }
  }

  typedef percentage-type {
    type uint8 {
      tailf:info
        "<1-100>;;Percentage";
      range "1..100";
    }
  }

  typedef ipv4-prefix {
    type string {
      pattern '(([0-9]|[1-9][0-9]|1[0-9][0-9]|2[0-4][0-9]|25[0-5])\.){3}([0-9]|[1-9][0-9]|1[0-9][0-9]|2[0-4][0-9]|25[0-5])/(([0-9])|([1-2][0-9])|(3[0-2]))';
    }
  }

  typedef ipv6-prefix {
    type string {
      pattern '((:|[0-9a-fA-F]{0,4}):)([0-9a-fA-F]{0,4}:){0,5}((([0-9a-fA-F]{0,4}:)?(:|[0-9a-fA-F]{0,4}))|(((25[0-5]|2[0-4][0-9]|[01]?[0-9]?[0-9])\.){3}(25[0-5]|2[0-4][0-9]|[01]?[0-9]?[0-9])))(/(([0-9])|([0-9]{2})|(1[0-1][0-9])|(12[0-8])))';
      pattern '(([^:]+:){6}(([^:]+:[^:]+)|(.*\..*)))|((([^:]+:)*[^:]+)?::(([^:]+:)*[^:]+)?)(/.+)';
    }
  }

  typedef host-type {
    type union {
      type inet:ip-address {
        tailf:info
          "";
      }
      type inet:domain-name {
        tailf:info
          "";
      }
    }
  }

  typedef rd-type {
    type string {
      tailf:info
        "ASN:nn or IP-address:nn;;VPN Route Distinguisher";
      pattern '(\d*(.\d*)*)?:(\d*(.\d*)*)?';
    }
  }

  typedef vpn-id-type {
    type string {
      tailf:info
        "OUI:VPN-Index;;, format (hex) <3 bytes OUI:4 bytes VPN_Index>";
      pattern '[0-9a-fA-F][0-9a-fA-F]?[0-9a-fA-F]?:[0-9a-fA-F][0-9a-fA-F]?[0-9a-fA-F]?[0-9a-fA-F]?';
    }
  }

  typedef asn-ip-type {
    type string {
      pattern '(([0-9]+)|((([0-9]|[1-9][0-9]|1[0-9][0-9]|2[0-4][0-9]|25[0-5])\.){3}([0-9]|[1-9][0-9]|1[0-9][0-9]|2[0-4][0-9]|25[0-5]))):[0-9]+';
      tailf:info
        "ASN:nn or IP-address:nn";
    }
  }

  typedef hhmm-type {
    type string {
      pattern '([0-1]?[0-9]|2[0-4]):([0-5][0-9])(:[0-5][0-9])?';
    }
  }

  typedef weekday-type {
    type enumeration {
      enum "Mon";
      enum "Tue";
      enum "Wed";
      enum "Thu";
      enum "Fri";
      enum "Sat";
      enum "Sun";
    }
  }

  typedef month-type {
    type enumeration {
      enum "Jan";
      enum "Feb";
      enum "Mar";
      enum "Apr";
      enum "May";
      enum "Jun";
      enum "Jul";
      enum "Aug";
      enum "Sep";
      enum "Oct";
      enum "Nov";
      enum "Dec";
    }
  }

  typedef std-acl-type {
    type union {
      type uint16 {
        tailf:info
          "<1-99>;;Standard IP access-list number";
        range "1..99";
      }
      type uint16 {
        tailf:info
          "<1300-1999>;;Standard IP access-list number (expanded range)";
        range "1300..1999";
      }
      type string {
        tailf:info
          "WORD;;Access-list name";
        pattern '[a-zA-Z].*';
      }
    }
  }

  typedef ext-acl-type {
    type union {
      type uint16 {
        tailf:info
          "<100-199>;;Access list number";
        range "100..199";
      }
      type uint16 {
        tailf:info
          "<2000-2699>;;Access list number (expanded range)";
        range "2000..2699";
      }
      type string {
        tailf:info
          "WORD;;IP Named Extended Access list";
        pattern '[a-zA-Z].*';
      }
    }
  }

  typedef exp-acl-type {
    type union {
      type uint16 {
        tailf:info
          "<1-199>;;IP access list (standard or extended)";
        range "1..199";
      }
      type uint16 {
        tailf:info
          "<1300-2699>;;IP expanded access list (standard or extended)";
        range "1300..2699";
      }
      type string {
        tailf:info
          "WORD;;Access-list name";
        pattern '[a-zA-Z].*';
      }
    }
  }

  typedef mdt-data-list-type {
    type union {
      type uint16 {
        tailf:info
          "<100-199>;;Access-list number";
        range "100..199";
      }
      type uint16 {
        tailf:info
          "<2000-2699>;;Access list number (expanded range)";
        range "2000..2699";
      }
      type string {
        tailf:info
          "WORD;;IP Named Extended Access list";
        pattern '[a-fA-F].*';
      }
    }
  }

  typedef ldp-discovery-address-type {
    type union {
      type enumeration {
        enum "interface" {
          tailf:code-name "ldp_interface";
          tailf:info
            "Use interface address for LDP transport address";
        }
      }
      type inet:ipv4-address {
        tailf:info
          "A.B.C.D;;IP address to use for LDP transport address";
      }
    }
  }

  typedef mst-cost-type {
    type union {
      type uint32 {
        tailf:info
          "<1-200000000>;;Port path cost";
        range "1..200000000";
      }
      type enumeration {
        enum "auto" {
          tailf:code-name "mst_cost_type_auto";
          tailf:info
            "Determine cost based on media speed of this interface";
        }
      }
    }
  }

  typedef spanning-tree-cost-type {
    type union {
      type uint32 {
        tailf:info
          "<1-200000000>;;Port path cost";
        range "1..200000000";
      }
      type enumeration {
        enum "auto" {
          tailf:code-name "spanning-tree-cost-type-auto";
          tailf:info
            "Determine cost based on media speed of this interface";
        }
      }
    }
  }

  typedef dscp-type {
    type union {
      type uint8 {
        tailf:info
          "<0-63>;;Differentiated services codepoint value";
        range "0..63";
      }
      type enumeration {
        enum "af11" {
          tailf:info
            "Match packets with AF11 dscp (001010)";
        }
        enum "af12" {
          tailf:info
            "Match packets with AF12 dscp (001100)";
        }
        enum "af13" {
          tailf:info
            "Match packets with AF13 dscp (001110)";
        }
        enum "af21" {
          tailf:info
            "Match packets with AF21 dscp (010010)";
        }
        enum "af22" {
          tailf:info
            "Match packets with AF22 dscp (010100)";
        }
        enum "af23" {
          tailf:info
            "Match packets with AF23 dscp (010110)";
        }
        enum "af31" {
          tailf:info
            "Match packets with AF31 dscp (011010)";
        }
        enum "af32" {
          tailf:info
            "Match packets with AF32 dscp (011100)";
        }
        enum "af33" {
          tailf:info
            "Match packets with AF33 dscp (011110)";
        }
        enum "af41" {
          tailf:info
            "Match packets with AF41 dscp (100010)";
        }
        enum "af42" {
          tailf:info
            "Match packets with AF42 dscp (100100)";
        }
        enum "af43" {
          tailf:info
            "Match packets with AF43 dscp (100110)";
        }
        enum "cs1" {
          tailf:info
            "Match packets with CS1(precedence 1) dscp (001000)";
        }
        enum "cs2" {
          tailf:info
            "Match packets with CS2(precedence 2) dscp (010000)";
        }
        enum "cs3" {
          tailf:info
            "Match packets with CS3(precedence 3) dscp (011000)";
        }
        enum "cs4" {
          tailf:info
            "Match packets with CS4(precedence 4) dscp (100000)";
        }
        enum "cs5" {
          tailf:info
            "Match packets with CS5(precedence 5) dscp (101000)";
        }
        enum "cs6" {
          tailf:info
            "Match packets with CS6(precedence 6) dscp (110000)";
        }
        enum "cs7" {
          tailf:info
            "Match packets with CS7(precedence 7) dscp (111000)";
        }
        enum "default" {
          tailf:code-name "dscp_default";
          tailf:info
            "Match packets with default dscp (000000)";
        }
        enum "dscp" {
          tailf:info
            "Set packet dscp from dscp";
        }
        enum "ef" {
          tailf:info
            "Match packets with EF dscp (101110)";
        }
        enum "precedence" {
          tailf:info
            "Set packet dscp from precedence";
        }
      }
    }
  }

  typedef precedence-type {
    type union {
      type uint8 {
        tailf:info
          "<0-7>;;Precedence value";
        range "0..7";
      }
      type enumeration {
        enum "critical" {
          tailf:info
            "Set packets with critical precedence (5)";
        }
        enum "flash" {
          tailf:info
            "Set packets with flash precedence (3)";
        }
        enum "flash-override" {
          tailf:info
            "Set packets with flash override precedence (4)";
        }
        enum "immediate" {
          tailf:info
            "Set packets with immediate precedence (2)";
        }
        enum "internet" {
          tailf:code-name "prec_internet";
          tailf:info
            "Set packets with internetwork control precedence (6)";
        }
        enum "network" {
          tailf:info
            "Set packets with network control precedence (7)";
        }
        enum "priority" {
          tailf:code-name "prec_priority";
          tailf:info
            "Set packets with priority precedence (1)";
        }
        enum "routine" {
          tailf:info
            "Set packets with routine precedence (0)";
        }
      }
    }
  }

  typedef precedence-type2 {
    type union {
      type uint8 {
        tailf:info
          "<0-7>;;IP precedence";
        range "0..7";
      }
      type enumeration {
        enum "rsvp" {
          tailf:code-name "prec_rsvp";
          tailf:info
            "rsvp traffic";
        }
      }
    }
  }

  typedef cos_value-type {
    type union {
      type uint8 {
        tailf:info
          "<0-7>;;new cos value";
        range "0..7";
      }
      type enumeration {
        enum "cos" {
          tailf:info
            "Set packet cos from cos";
        }
        enum "dscp" {
          tailf:info
            "Set packet cos from dscp";
        }
        enum "exp" {
          tailf:info
            "Set packet cos from exp";
        }
        enum "precedence" {
          tailf:info
            "Set packet cos from precedence";
        }
      }
    }
  }

  typedef qos_value-type {
    type union {
      type uint8 {
        tailf:info
          "<0-99>;;new qos-group";
        range "0..99";
      }
      type enumeration {
        enum "cos" {
          tailf:info
            "Set packet qos from cos";
        }
        enum "dscp" {
          tailf:info
            "Set packet qos from dscp";
        }
        enum "exp" {
          tailf:info
            "Set packet qos from exp";
        }
        enum "precedence" {
          tailf:info
            "Set packet qos from precedence";
        }
      }
    }
  }

  typedef exp_value-type {
    type union {
      type uint8 {
        tailf:info
          "<0-7>;;new exp";
        range "0..7";
      }
      type enumeration {
        enum "cos" {
          tailf:info
            "Set packet exp from cos";
        }
        enum "dscp" {
          tailf:info
            "Set packet exp from dscp";
        }
        enum "exp" {
          tailf:info
            "Set packet exp from exp";
        }
        enum "precedence" {
          tailf:info
            "Set packet exp from precedence";
        }
      }
    }
  }

  typedef prec_value-type {
    type union {
      type uint8 {
        tailf:info
          "<0-7>;;new precedence";
        range "0..7";
      }
      type enumeration {
        enum "cos" {
          tailf:info
            "Set packet precedence from cos";
        }
        enum "dscp" {
          tailf:info
            "Set packet precedence from dscp";
        }
        enum "exp" {
          tailf:info
            "Set packet precedence from exp";
        }
        enum "precedence" {
          tailf:info
            "Set packet precedence from precedence";
        }
      }
    }
  }

  typedef access-list-standard-id-type {
    type union {
      type default-access-list-standard-id-type;
      type string {
        tailf:info
          "WORD;;Standard access-list name";
      }
    }
  }

  typedef default-access-list-standard-id-type {
    type union {
      type uint8 {
        tailf:info
          "<1-99>;;IP Standard access list number";
        range "1..99";
      }
      type uint16 {
        tailf:info
          "<1300-1999>;;IP Standard expanded access list number";
        range "1300..1999";
      }
    }
  }

  typedef access-list-in-out-type {
    type enumeration {
      enum "in" {
        tailf:info
          "Filter incoming routing updates";
      }
      enum "out" {
        tailf:info
          "Filter outgoing routing updates";
      }
    }
  }

  typedef redist-ospf-external-type {
    type enumeration {
      enum "1" {
        tailf:info
          "Redistribute external type 1 routes";
      }
      enum "2" {
        tailf:info
          "Redistribute external type 2 routes";
      }
    }
  }

  typedef class-name-type {
    type union {
      type string {
        tailf:info
          "WORD;;class-map name";
      }
      type enumeration {
        enum "class-default" {
          tailf:info
            "System default class matching otherwise unclassified packet";
        }
      }
    }
  }

  typedef access-list-type {
    type union {
      type uint16 {
        range "1..199";
        tailf:info
          "<1-199>;;Access list";
      }
      type uint16 {
        range "1300..2699";
        tailf:info
          "<1300-2699>;;Access list (expanded range)";
      }
    }
  }

  typedef bgp-distribute-list-type {
    type union {
      type uint16 {
        range "100..199";
        tailf:info
          "<100-199>;;IP access-list number";
      }
      type uint16 {
        range "2000..2699";
        tailf:info
          "<2000-2699>;;IP expanded access list number";
      }
      type string {
        tailf:info
          "WORD;;Access-list name";
        pattern '[a-zA-Z].*';
      }
    }
  }

  typedef bgp-distribute-list-type2 {
    type union {
      type uint16 {
        range "1..199";
        tailf:info
          "<1-199>;;IP access list number";
      }
      type uint16 {
        range "1300..2699";
        tailf:info
          "<1300-2699>;;IP access list number (expanded range)";
      }
      type string {
        tailf:info
          "WORD;;Access-list name";
        pattern '[a-zA-Z].*';
      }
    }
  }

  typedef ospf-area-type {
    type union {
      type uint32 {
        range "0 .. 4294967295";
        tailf:info
          "<0-4294967295>;;OSPF area ID as a decimal value";
      }
      type inet:ipv4-address {
        tailf:info
          "A.B.C.D;;OSPF area ID in IP address format";
      }
    }
  }

  typedef ospf-metric-type {
    type uint32 {
      range "1 .. 2";
      tailf:info
        "<1-2>;;OSPF Link State type";
    }
  }

  typedef limit-dc-non-dc-type {
    type union {
      type uint32 {
        range "1 .. 255";
        tailf:info
          "<1-255>;;The maximum number of retransmissions";
      }
      type enumeration {
        enum "disable" {
          tailf:info
            "Disable the feature";
        }
      }
    }
  }

  typedef default-access-list-id-type {
    type union {
      type uint32 {
        range "1 .. 199";
        tailf:info
          "<1-199>;;IP access list number";
      }
      type uint32 {
        range "1300 .. 2699";
        tailf:info
          "<1300-2699>;;IP expanded access list number";
      }
    }
  }

  typedef access-list-id-type {
    type union {
      type default-access-list-id-type;
      type string {
        tailf:info
          "WORD;;Access-list name";
        pattern '[a-zA-Z].*';
      }
    }
  }

  typedef default-offset-list-id-type {
    type union {
      type uint32 {
        range "0 .. 99";
        tailf:info
          "<0-99>;;Access list of networks to apply offset (0 selects all networks)";
      }
      type uint32 {
        range "1300 .. 1999";
        tailf:info
          "<1300-1999>;;Access list of networks to apply offset (expanded range)";
      }
    }
  }

  typedef offset-list-id-type {
    type union {
      type default-offset-list-id-type;
      type string {
        tailf:info
          "WORD;;Access-list name";
        pattern '[a-zA-Z].*';
      }
    }
  }

  typedef offset-list-in-out-type {
    type enumeration {
      enum "in" {
        tailf:info
          "Perform offset on incoming updates";
      }
      enum "out" {
        tailf:info
          "Perform offset on outgoing updates";
      }
    }
  }

  typedef isis-net {
    tailf:info
      "XX.XXXX. ... .XXX.XX;;Network entity title (NET)";
    type string {
      pattern '(([0-9a-fA-F]{2}\.[0-9a-fA-F]{4})|[0-9a-fA-F]{4})\.([0-9a-fA-F]{4}\.){3,10}00';
    }
  }

  typedef isis-level-type {
    type enumeration {
      enum "level-1" {
        tailf:info
          "Level-1 only";
      }
      enum "level-1-2" {
        tailf:info
          "Level-1-2";
      }
      enum "level-2" {
        tailf:info
          "Level-2 only";
      }
    }
  }

  typedef isis-routes-level-type {
    type enumeration {
      enum "level-1" {
        tailf:info
          "IS-IS level-1 routes only";
      }
      enum "level-1-2" {
        tailf:info
          "IS-IS level-1 and level-2 routes";
      }
      enum "level-2" {
        tailf:info
          "IS-IS level-2 routes only";
      }
    }
  }

  typedef authentication-level-type {
    type enumeration {
      enum "level-1" {
        tailf:info
          "ISIS authentication for level-1";
      }
      enum "level-2" {
        tailf:info
          "ISIS authentication for level-2";
      }
    }
  }

  typedef logging-level-type {
    type union {
      type uint16 {
        tailf:info
          "<0-7>;;Logging severity level";
        range "0..7";
      }
      type enumeration {
        enum "alerts" {
          tailf:info
            "Immediate action needed (severity=1)";
        }
        enum "critical" {
          tailf:info
            "Critical conditions (severity=2)";
        }
        enum "debugging" {
          tailf:info
            "Debugging messages (severity=7)";
        }
        enum "emergencies" {
          tailf:info
            "System is unusable (severity=0)";
        }
        enum "errors" {
          tailf:info
            "Error conditions (severity=3)";
        }
        enum "informational" {
          tailf:info
            "Informational messages (severity=6)";
        }
        enum "notifications" {
          tailf:info
            "Normal but significant conditions (severity=5)";
        }
        enum "warnings" {
          tailf:info
            "Warning conditions (severity=4)";
        }
      }
    }
  }

  typedef operator-type {
    type enumeration {
      enum "eq" {
        tailf:info
          "Equal to";
      }
      enum "ge" {
        tailf:info
          "Greater than or equal to";
      }
      enum "gt" {
        tailf:info
          "Greater than";
      }
      enum "le" {
        tailf:info
          "Less than or equal to";
      }
      enum "lt" {
        tailf:info
          "Less than";
      }
      enum "ne" {
        tailf:info
          "Not equal to";
      }
    }
  }

  typedef police-packets-bytes-type {
    type enumeration {
      enum "packets" {
        tailf:info
          "Treat 'burst' value as packets";
      }
      enum "bytes" {
        tailf:info
          "Treat 'burst' value as bytes";
      }
    }
  }

  typedef police-pps-bps-type {
    type enumeration {
      enum "pps" {
        tailf:info
          "pps  Treat 'rate' value in packets-per-second";
      }
      enum "bps" {
        tailf:info
          "pps  Treat 'rate' value in bytes-per-second";
      }
    }
  }

  typedef police-bps-type {
    type uint64 {
      tailf:info
        "<8000-64000000000>;;Bits per second";
      range "8000..64000000000";
    }
  }

  typedef police-burst-type {
    type uint32 {
      tailf:info
        "<1000-512000000>;;Burst bytes";
      range "1000..512000000";
    }
  }

  grouping ncs_compliance_template_vrf-route-target-grouping {
    list export {
      // NCS patched for predictable order
      ordered-by user;
      tailf:cli-suppress-mode;
      key "asn-ip";
      leaf asn-ip {
        type ncs_compliance_template_asn-ip-type;
      }
    }
    list import {
      // NCS patched for predictable order
      ordered-by user;
      tailf:cli-suppress-mode;
      key "asn-ip";
      leaf asn-ip {
        type ncs_compliance_template_asn-ip-type;
      }
    }
  }

  grouping ncs_compliance_template_police-action-transmit-grouping {
    leaf transmit {
      type empty;
    }
  }

  grouping ncs_compliance_template_police-action-drop-grouping {
    leaf drop {
      type empty;
    }
  }

  grouping ncs_compliance_template_police-conform-action-grouping {
    container conform-set-clp-transmit {
      tailf:cli-drop-node-name;
      container conform-action {
        leaf set-clp-transmit {
          type empty;
        }
      }
    }
    container conform-set-cos-transmit {
      tailf:cli-drop-node-name;
      container conform-action {
        leaf set-cos-transmit {
          type ncs_compliance_template_cos_value-type;
        }
      }
    }
    container conform-set-cos-transmit-table {
      tailf:cli-drop-node-name;
      container conform-action {
        leaf set-cos-transmit {
          type ncs_compliance_template_cos_value-type;
        }
        leaf table {
          type string;
        }
      }
    }
    container conform-set-discard-class-transmit {
      tailf:cli-drop-node-name;
      container conform-action {
        leaf set-discard-class-transmit {
          type string;
        }
      }
    }
    container conform-set-dscp-transmit {
      tailf:cli-drop-node-name;
      container conform-action {
        leaf set-dscp-transmit {
          type ncs_compliance_template_dscp-type;
        }
      }
    }
    container conform-set-dscp-transmit-table {
      tailf:cli-drop-node-name;
      container conform-action {
        leaf set-dscp-transmit {
          type ncs_compliance_template_dscp-type;
        }
        leaf table {
          type string;
        }
      }
    }
    container conform-set-frde-transmit {
      tailf:cli-drop-node-name;
      container conform-action {
        leaf set-frde-transmit {
          type empty;
        }
      }
    }
    container conform-set-mpls-exp-imposition-transmit {
      tailf:cli-drop-node-name;
      container conform-action {
        leaf set-mpls-exp-imposition-transmit {
          type ncs_compliance_template_exp_value-type;
        }
      }
    }
    container conform-set-mpls-exp-imposition-transmit-table {
      tailf:cli-drop-node-name;
      container conform-action {
        leaf set-mpls-exp-imposition-transmit {
          type ncs_compliance_template_exp_value-type;
        }
        leaf table {
          type string;
        }
      }
    }
    container conform-set-mpls-exp-topmost-transmit {
      tailf:cli-drop-node-name;
      container conform-action {
        leaf set-mpls-exp-topmost-transmit {
          type ncs_compliance_template_exp_value-type;
        }
      }
    }
    container conform-set-mpls-exp-topmost-transmit-table {
      tailf:cli-drop-node-name;
      container conform-action {
        leaf set-mpls-exp-topmost-transmit {
          type ncs_compliance_template_exp_value-type;
        }
        leaf table {
          type string;
        }
      }
    }
    container conform-set-prec-transmit {
      tailf:cli-drop-node-name;
      container conform-action {
        leaf set-prec-transmit {
          type ncs_compliance_template_prec_value-type;
        }
      }
    }
    container conform-set-prec-transmit-table {
      tailf:cli-drop-node-name;
      container conform-action {
        leaf set-prec-transmit {
          type ncs_compliance_template_prec_value-type;
        }
        leaf table {
          type string;
        }
      }
    }
    container conform-set-qos-transmit {
      tailf:cli-drop-node-name;
      container conform-action {
        leaf set-qos-transmit {
          type ncs_compliance_template_qos_value-type;
        }
      }
    }
    container conform-set-qos-transmit-table {
      tailf:cli-drop-node-name;
      container conform-action {
        leaf set-qos-transmit {
          type ncs_compliance_template_qos_value-type;
        }
        leaf table {
          type string;
        }
      }
    }
    container conform-transmit {
      tailf:cli-drop-node-name;
      container conform-action {
        uses ncs_compliance_template_police-action-transmit-grouping;
      }
    }
    container conform-drop {
      tailf:cli-drop-node-name;
      container conform-action {
        uses ncs_compliance_template_police-action-drop-grouping;
      }
    }
  }

  grouping ncs_compliance_template_police-exceed-action-grouping {
    container exceed-dscp {
      tailf:cli-drop-node-name;
      container exceed-action {
        leaf dscp {
          type ncs_compliance_template_dscp-type;
        }
      }
    }
    container exceed-set-clp-transmit {
      tailf:cli-drop-node-name;
      container exceed-action {
        leaf set-clp-transmit {
          type empty;
        }
      }
    }
    container exceed-set-cos-transmit {
      tailf:cli-drop-node-name;
      container exceed-action {
        leaf set-cos-transmit {
          type ncs_compliance_template_cos_value-type;
        }
      }
    }
    container exceed-set-discard-class-transmit {
      tailf:cli-drop-node-name;
      container exceed-action {
        leaf set-discard-class-transmit {
          type string;
        }
      }
    }
    container exceed-set-dscp-transmit {
      tailf:cli-drop-node-name;
      container exceed-action {
        leaf set-dscp-transmit {
          type ncs_compliance_template_dscp-type;
        }
      }
    }
    container exceed-set-frde-transmit {
      tailf:cli-drop-node-name;
      container exceed-action {
        leaf set-frde-transmit {
          type empty;
        }
      }
    }
    container exceed-set-mpls-exp-imposition-transmit {
      tailf:cli-drop-node-name;
      container exceed-action {
        leaf set-mpls-exp-imposition-transmit {
          type ncs_compliance_template_exp_value-type;
        }
      }
    }
    container exceed-set-mpls-exp-topmost-transmit {
      tailf:cli-drop-node-name;
      container exceed-action {
        leaf set-mpls-exp-topmost-transmit {
          type ncs_compliance_template_exp_value-type;
        }
      }
    }
    container exceed-set-prec-transmit {
      tailf:cli-drop-node-name;
      container exceed-action {
        leaf set-prec-transmit {
          type ncs_compliance_template_prec_value-type;
        }
      }
    }
    container exceed-set-qos-transmit {
      tailf:cli-drop-node-name;
      container exceed-action {
        leaf set-qos-transmit {
          type ncs_compliance_template_qos_value-type;
        }
      }
    }
    container exceed-transmit {
      tailf:cli-drop-node-name;
      container exceed-action {
        uses ncs_compliance_template_police-action-transmit-grouping;
      }
    }
    container exceed-drop {
      tailf:cli-drop-node-name;
      container exceed-action {
        uses ncs_compliance_template_police-action-drop-grouping;
      }
    }
  }

  grouping ncs_compliance_template_police-violate-action-grouping {
    container violate-set-clp-transmit {
      tailf:cli-drop-node-name;
      container violate-action {
        leaf set-clp-transmit {
          type empty;
        }
      }
    }
    container violate-set-cos-transmit {
      tailf:cli-drop-node-name;
      container violate-action {
        leaf set-cos-transmit {
          type ncs_compliance_template_cos_value-type;
        }
      }
    }
    container violate-set-discard-class-transmit {
      tailf:cli-drop-node-name;
      container violate-action {
        leaf set-discard-class-transmit {
          type string;
        }
      }
    }
    container violate-set-dscp-transmit {
      tailf:cli-drop-node-name;
      container violate-action {
        leaf set-dscp-transmit {
          type ncs_compliance_template_dscp-type;
        }
      }
    }
    container violate-set-frde-transmit {
      tailf:cli-drop-node-name;
      container violate-action {
        leaf set-frde-transmit {
          type empty;
        }
      }
    }
    container violate-set-mpls-exp-imposition-transmit {
      tailf:cli-drop-node-name;
      container violate-action {
        leaf set-mpls-exp-imposition-transmit {
          type ncs_compliance_template_exp_value-type;
        }
      }
    }
    container violate-set-mpls-exp-topmost-transmit {
      tailf:cli-drop-node-name;
      container violate-action {
        leaf set-mpls-exp-topmost-transmit {
          type ncs_compliance_template_exp_value-type;
        }
      }
    }
    container violate-set-prec-transmit {
      tailf:cli-drop-node-name;
      container violate-action {
        leaf set-prec-transmit {
          type ncs_compliance_template_prec_value-type;
        }
      }
    }
    container violate-set-qos-transmit {
      tailf:cli-drop-node-name;
      container violate-action {
        leaf set-qos-transmit {
          type ncs_compliance_template_qos_value-type;
        }
      }
    }
    container violate-transmit {
      tailf:cli-drop-node-name;
      container violate-action {
        uses ncs_compliance_template_police-action-transmit-grouping;
      }
    }
    container violate-drop {
      tailf:cli-drop-node-name;
      container violate-action {
        uses ncs_compliance_template_police-action-drop-grouping;
      }
    }
  }

  grouping ncs_compliance_template_police-action-grouping {
    container actions {
      tailf:cli-drop-node-name;
      uses ncs_compliance_template_police-conform-action-grouping;
      uses ncs_compliance_template_police-exceed-action-grouping;
      uses ncs_compliance_template_police-violate-action-grouping;
    }
  }

  grouping ncs_compliance_template_password-grouping {
    container password-container {
      tailf:cli-drop-node-name;
      leaf encryption {
        tailf:cli-drop-node-name;
        type string;
        // NCS drop default statement
      }
      leaf password {
        tailf:cli-drop-node-name;
        type string;
      }
    }
  }

  grouping ncs_compliance_template_distribute-list-grouping {
    container distribute-list {
      list accesslist {
        // NCS patched for predictable order
        ordered-by user;
        tailf:cli-drop-node-name;
        tailf:cli-suppress-mode;
        key "in-out";
        leaf in-out {
          type ncs_compliance_template_access-list-in-out-type;
        }
      }
      list accesslist-ifname {
        // NCS patched for predictable order
        ordered-by user;
        tailf:cli-drop-node-name;
        tailf:cli-suppress-mode;
        // NCS drop tailf-common:cli-diff-dependency statement
        key "in-out interface";
        leaf in-out {
          type ncs_compliance_template_access-list-in-out-type;
        }
        leaf interface {
          type string;
        }
      }
      list accesslist-prefix-gateway {
        // NCS patched for predictable order
        ordered-by user;
        tailf:cli-drop-node-name;
        tailf:cli-suppress-mode;
        key "in-out";
        leaf prefix-gateway {
          tailf:cli-drop-node-name;
          // NCS drop mandatory statement
          type string;
        }
        leaf name {
          tailf:cli-drop-node-name;
          // NCS drop mandatory statement
          type string;
        }
        leaf in-out {
          type ncs_compliance_template_access-list-in-out-type;
        }
      }
      list accesslist-prefix-gateway-ifname {
        // NCS patched for predictable order
        ordered-by user;
        tailf:cli-drop-node-name;
        tailf:cli-suppress-mode;
        key "in-out interface";
        leaf prefix-gateway {
          tailf:cli-drop-node-name;
          // NCS drop mandatory statement
          type string;
        }
        leaf name {
          tailf:cli-drop-node-name;
          // NCS drop mandatory statement
          type string;
        }
        leaf in-out {
          type ncs_compliance_template_access-list-in-out-type;
        }
        leaf interface {
          type string;
        }
      }
    }
  }

  grouping ncs_compliance_template_passive-interface-grouping {
    container passive-interface {
      choice passive-interface-choice {
        leaf default {
          type empty;
        }
        leaf interface {
          tailf:cli-drop-node-name;
          type string;
        }
      }
    }
    container disable {
      // NCS drop when statement
      list passive-interface {
        // NCS patched for predictable order
        ordered-by user;
        tailf:cli-suppress-mode;
        key "interface";
        leaf interface {
          tailf:cli-drop-node-name;
          type string;
        }
      }
    }
  }

  grouping ncs_compliance_template_interface-grouping {
    choice interface-choice {
      leaf Embedded-Service-Engine {
        type string;
      }
      leaf FastEthernet {
        type string;
      }
      leaf GigabitEthernet {
        type string;
      }
      leaf Loopback {
        type string;
      }
      leaf Multilink {
        type string;
      }
      leaf Port-channel {
        type string;
      }
      leaf Serial {
        type string;
      }
      leaf TenGigabitEthernet {
        type string;
      }
      leaf Virtual-Template {
        type string;
      }
      leaf Vlan {
        type string;
      }
    }
  }

  grouping ncs_compliance_template_ethernet-grouping {
    choice ethernet-choice {
      leaf FastEthernet {
        type string;
      }
      leaf GigabitEthernet {
        type string;
      }
      leaf Port-channel {
        type string;
      }
      leaf TenGigabitEthernet {
        type string;
      }
    }
  }

  grouping ncs_compliance_template_ip-community-list-standard-grouping {
    container deny {
      presence "Specify community to reject";
      list deny-list {
        // NCS patched for predictable order
        ordered-by user;
        tailf:cli-drop-node-name;
        tailf:cli-suppress-mode;
        key "expr";
        leaf expr {
          type string;
        }
      }
    }
    container permit {
      presence "Specify community to accept";
      list permit-list {
        // NCS patched for predictable order
        ordered-by user;
        tailf:cli-drop-node-name;
        tailf:cli-suppress-mode;
        key "expr";
        leaf expr {
          type string;
        }
      }
    }
  }

  grouping ncs_compliance_template_ip-community-list-expanded-grouping {
    container deny {
      presence "Specify community to reject";
      list deny-list {
        // NCS patched for predictable order
        ordered-by user;
        tailf:cli-suppress-mode;
        tailf:cli-drop-node-name;
        key "expr";
        leaf expr {
          type string;
        }
      }
    }
    container permit {
      presence "Specify community to accept";
      list permit-list {
        // NCS patched for predictable order
        ordered-by user;
        tailf:cli-suppress-mode;
        tailf:cli-drop-node-name;
        key "expr";
        leaf expr {
          type string;
        }
      }
    }
  }

  grouping ncs_compliance_template_ip-route-options-grouping {
    leaf metric {
      tailf:cli-drop-node-name;
      type string;
    }
    leaf global {
      type empty;
    }
    leaf name {
      type string;
    }
    leaf permanent {
      type empty;
    }
    leaf multicast {
      type empty;
    }
    leaf dhcp {
      type empty;
    }
    leaf tag {
      type string;
    }
    leaf track {
      type string;
    }
  }

  grouping ncs_compliance_template_ip-route-grouping {
    list ip-route-interface-forwarding-list {
      // NCS patched for predictable order
      ordered-by user;
      tailf:cli-drop-node-name;
      tailf:cli-suppress-mode;
      key "prefix mask interface forwarding-address";
      leaf prefix {
        type string;
      }
      leaf mask {
        type string;
      }
      leaf interface {
        // NCS drop tailf-common:cli-diff-dependency statement
        type string;
      }
      leaf forwarding-address {
        type string;
      }
      uses ncs_compliance_template_ip-route-options-grouping;
    }
    list ip-route-forwarding-list {
      // NCS patched for predictable order
      ordered-by user;
      tailf:cli-drop-node-name;
      tailf:cli-suppress-mode;
      key "prefix mask forwarding-address";
      leaf prefix {
        type string;
      }
      leaf mask {
        type string;
      }
      leaf forwarding-address {
        type string;
      }
      uses ncs_compliance_template_ip-route-options-grouping;
    }
    list ip-route-interface-list {
      // NCS patched for predictable order
      ordered-by user;
      tailf:cli-drop-node-name;
      tailf:cli-suppress-mode;
      key "prefix mask interface";
      leaf prefix {
        type string;
      }
      leaf mask {
        type string;
      }
      leaf interface {
        // NCS drop tailf-common:cli-diff-dependency statement
        type string;
      }
      uses ncs_compliance_template_ip-route-options-grouping;
    }
  }

  grouping ncs_compliance_template_ipv6-route-options-grouping {
    leaf distance {
      tailf:cli-drop-node-name;
      type string;
    }
    choice type-choice {
      leaf multicast {
        type empty;
      }
      leaf unicast {
        type empty;
      }
    }
    leaf tag {
      type string;
    }
  }

  grouping ncs_compliance_template_ipv6-route-entry-grouping {
    list ipv6-destination-list {
      // NCS patched for predictable order
      ordered-by user;
      tailf:cli-drop-node-name;
      tailf:cli-suppress-mode;
      key "destination";
      leaf destination {
        type string;
      }
      uses ncs_compliance_template_ipv6-route-options-grouping;
    }
  }

  grouping ncs_compliance_template_ipv6-route-grouping {
    list ipv6-route-list {
      // NCS patched for predictable order
      ordered-by user;
      tailf:cli-drop-node-name;
      tailf:cli-suppress-mode;
      key "prefix";
      leaf prefix {
        type ncs_compliance_template_ipv6-prefix;
      }
      uses ncs_compliance_template_ipv6-route-entry-grouping;
      list FastEthernet {
        // NCS patched for predictable order
        ordered-by user;
        tailf:cli-suppress-mode;
        key "name";
        leaf name {
          type string;
        }
        uses ncs_compliance_template_ipv6-route-entry-grouping;
        uses ncs_compliance_template_ipv6-route-options-grouping;
      }
      list Null {
        // NCS patched for predictable order
        ordered-by user;
        tailf:cli-suppress-mode;
        key "name";
        leaf name {
          type string;
        }
        uses ncs_compliance_template_ipv6-route-entry-grouping;
        uses ncs_compliance_template_ipv6-route-options-grouping;
      }
    }
  }

  grouping ncs_compliance_template_random-detect-grouping {
    leaf min-threshold {
      tailf:cli-drop-node-name;
      type string;
    }
    leaf max-threshold {
      tailf:cli-drop-node-name;
      type string;
    }
    leaf denominator {
      tailf:cli-drop-node-name;
      type string;
    }
  }

  grouping ncs_compliance_template_class-map-match-grouping {
    container access-group {
      leaf index {
        tailf:cli-drop-node-name;
        type string;
      }
      leaf-list name {
        // NCS patched for predictable order
        ordered-by user;
        type string;
      }
    }
    leaf any {
      type empty;
    }
    leaf-list class-map {
      // NCS patched for predictable order
      ordered-by user;
      type string;
    }
    leaf-list cos {
      // NCS patched for predictable order
      ordered-by user;
      type string;
    }
    container destination-address {
      leaf-list mac {
        // NCS patched for predictable order
        ordered-by user;
        type string;
      }
    }
    leaf-list discard-class {
      // NCS patched for predictable order
      ordered-by user;
      type string;
    }
    leaf-list dscp {
      // NCS patched for predictable order
      ordered-by user;
      type ncs_compliance_template_dscp-type;
    }
    leaf fr-de {
      type empty;
    }
    leaf-list fr-dlci {
      // NCS patched for predictable order
      ordered-by user;
      type string;
    }
    leaf-list input-interface {
      // NCS patched for predictable order
      ordered-by user;
      type string;
    }
    container ip {
      leaf-list dscp {
        // NCS patched for predictable order
        ordered-by user;
        type ncs_compliance_template_dscp-type;
      }
      leaf-list precedence {
        // NCS patched for predictable order
        ordered-by user;
        type ncs_compliance_template_precedence-type;
      }
      list rtp {
        // NCS patched for predictable order
        ordered-by user;
        key "port1 port2";
        leaf port1 {
          type string;
        }
        leaf port2 {
          type string;
        }
      }
    }
    container mpls {
      container experimental {
        leaf-list topmost {
          // NCS patched for predictable order
          ordered-by user;
          type string;
        }
      }
    }
    container packet {
      container length {
        leaf max {
          type string;
        }
        leaf min {
          type string;
        }
      }
    }
    leaf-list precedence {
      // NCS patched for predictable order
      ordered-by user;
      type ncs_compliance_template_precedence-type;
    }
    container protocol {
      leaf x802-11-iapp {
        tailf:alt-name "802-11-iapp";
        type empty;
      }
      leaf ace-svr {
        type empty;
      }
      leaf aol {
        type empty;
      }
      leaf appleqtc {
        type empty;
      }
      leaf biff {
        type empty;
      }
      leaf bittorrent {
        type empty;
      }
      leaf bootpc {
        type empty;
      }
      leaf bootps {
        type empty;
      }
      leaf cddbp {
        type empty;
      }
      leaf cifs {
        type empty;
      }
      leaf cisco-fna {
        type empty;
      }
      leaf cisco-net-mgmt {
        type empty;
      }
      leaf cisco-svcs {
        type empty;
      }
      leaf cisco-sys {
        type empty;
      }
      leaf cisco-tdp {
        type empty;
      }
      leaf cisco-tna {
        type empty;
      }
      leaf citriximaclient {
        type empty;
      }
      leaf clp {
        type empty;
      }
      leaf creativepartnr {
        type empty;
      }
      leaf creativeserver {
        type empty;
      }
      leaf daytime {
        type empty;
      }
      leaf dbase {
        type empty;
      }
      leaf dbcontrol_agent {
        type empty;
      }
      leaf ddns-v3 {
        type empty;
      }
      leaf dhcp-failover {
        type empty;
      }
      leaf directconnect {
        type empty;
      }
      leaf discard {
        type empty;
      }
      leaf dnsix {
        type empty;
      }
      leaf echo {
        type empty;
      }
      leaf entrust-svc-hdlr {
        type empty;
      }
      leaf entrust-svcs {
        type empty;
      }
      leaf exec {
        type empty;
      }
      leaf fcip-port {
        type empty;
      }
      leaf ftps {
        type empty;
      }
      leaf gdoi {
        type empty;
      }
      leaf giop {
        type empty;
      }
      leaf gtpv0 {
        type empty;
      }
      leaf gtpv1 {
        type empty;
      }
      leaf h225ras {
        type empty;
      }
      leaf h323callsigalt {
        type empty;
      }
      leaf hp-alarm-mgr {
        type empty;
      }
      leaf hp-collector {
        type empty;
      }
      leaf hp-managed-node {
        type empty;
      }
      leaf hsrp {
        type empty;
      }
      leaf https {
        type empty;
      }
      leaf ica {
        type empty;
      }
      leaf icabrowser {
        type empty;
      }
      leaf ident {
        type empty;
      }
      leaf igmpv3lite {
        type empty;
      }
      leaf imap3 {
        type empty;
      }
      leaf imaps {
        type empty;
      }
      leaf ipass {
        type empty;
      }
      leaf ipsec-msft {
        type empty;
      }
      leaf irc-serv {
        type empty;
      }
      leaf ircs {
        type empty;
      }
      leaf ircu {
        type empty;
      }
      leaf isakmp {
        type empty;
      }
      leaf iscsi {
        type empty;
      }
      leaf iscsi-target {
        type empty;
      }
      leaf kermit {
        type empty;
      }
      leaf ldap-admin {
        type empty;
      }
      leaf ldaps {
        type empty;
      }
      leaf login {
        type empty;
      }
      leaf lotusmtap {
        type empty;
      }
      leaf lotusnote {
        type empty;
      }
      leaf microsoft-ds {
        type empty;
      }
      leaf ms-cluster-net {
        type empty;
      }
      leaf ms-dotnetster {
        type empty;
      }
      leaf ms-sna {
        type empty;
      }
      leaf ms-sql {
        type empty;
      }
      leaf ms-sql-m {
        type empty;
      }
      leaf msexch-routing {
        type empty;
      }
      leaf msnmsgr {
        type empty;
      }
      leaf msrpc {
        type empty;
      }
      leaf mysql {
        type empty;
      }
      leaf n2h2server {
        type empty;
      }
      leaf ncp {
        type empty;
      }
      leaf net8-cman {
        type empty;
      }
      leaf netbios-dgm {
        type empty;
      }
      leaf netbios-ns {
        type empty;
      }
      leaf netbios-ssn {
        type empty;
      }
      leaf netstat {
        type empty;
      }
      leaf oem-agent {
        type empty;
      }
      leaf oracle {
        type empty;
      }
      leaf oracle-em-vp {
        type empty;
      }
      leaf oraclenames {
        type empty;
      }
      leaf orasrv {
        type empty;
      }
      leaf pcanywheredata {
        type empty;
      }
      leaf pcanywherestat {
        type empty;
      }
      leaf pop3s {
        type empty;
      }
      leaf pwdgen {
        type empty;
      }
      leaf qmtp {
        type empty;
      }
      leaf r-winsock {
        type empty;
      }
      leaf radius {
        type empty;
      }
      leaf rdb-dbs-disp {
        type empty;
      }
      leaf realmedia {
        type empty;
      }
      leaf realsecure {
        type empty;
      }
      leaf router {
        type empty;
      }
      leaf rsvp-encap {
        type empty;
      }
      leaf rsvp_tunnel {
        type empty;
      }
      leaf rtc-pm-port {
        type empty;
      }
      leaf rtelnet {
        type empty;
      }
      leaf send {
        type empty;
      }
      leaf shell {
        type empty;
      }
      leaf sip-tls {
        type empty;
      }
      leaf sms {
        type empty;
      }
      leaf snmptrap {
        type empty;
      }
      leaf sql-net {
        type empty;
      }
      leaf sqlserv {
        type empty;
      }
      leaf sqlsrv {
        type empty;
      }
      leaf sshell {
        type empty;
      }
      leaf ssp {
        type empty;
      }
      leaf syslog-conn {
        type empty;
      }
      leaf tacacs {
        type empty;
      }
      leaf tacacs-ds {
        type empty;
      }
      leaf tarantella {
        type empty;
      }
      leaf tcp {
        type empty;
      }
      leaf telnets {
        type empty;
      }
      leaf time {
        type empty;
      }
      leaf timed {
        type empty;
      }
      leaf tr-rsrb {
        type empty;
      }
      leaf ttc {
        type empty;
      }
      leaf udp {
        type empty;
      }
      leaf uucp {
        type empty;
      }
      leaf vqp {
        type empty;
      }
      leaf webster {
        type empty;
      }
      leaf who {
        type empty;
      }
      leaf wins {
        type empty;
      }
      leaf x11 {
        type empty;
      }
      leaf xdmcp {
        type empty;
      }
      leaf ymsgr {
        type empty;
      }
      leaf aarp {
        type empty;
      }
      leaf appletalk {
        type empty;
      }
      leaf arp {
        type empty;
      }
      leaf bgp {
        type empty;
      }
      leaf bridge {
        type empty;
      }
      leaf bstun {
        type empty;
      }
      leaf cdp {
        type empty;
      }
      container citrix {
        presence "enable citrix system protocol matching";
        leaf ica-tag {
          type string;
        }
      }
      leaf clns {
        type empty;
      }
      leaf clns_es {
        type empty;
      }
      leaf clns_is {
        type empty;
      }
      leaf cmns {
        type empty;
      }
      leaf compressedtcp {
        type empty;
      }
      leaf cuseeme {
        type empty;
      }
      leaf decnet {
        type empty;
      }
      leaf decnet_node {
        type empty;
      }
      leaf decnet_router-l1 {
        type empty;
      }
      leaf decnet_router-l2 {
        type empty;
      }
      leaf dhcp {
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        presence "enable fasttrack matching";
        leaf file-transfer {
          type string;
        }
      }
      leaf finger {
        type empty;
      }
      leaf ftp {
        type empty;
      }
      container gnutella {
        presence "enable gnutella matching";
        leaf file-transfer {
          type string;
        }
      }
      leaf gopher {
        type empty;
      }
      leaf gre {
        type empty;
      }
      leaf h323 {
        type empty;
      }
      container http {
        presence "enable http traffic matching";
        leaf c-header-field {
          type string;
        }
        leaf host {
          type string;
        }
        leaf mime {
          type string;
        }
        leaf s-header-field {
          type string;
        }
        leaf url {
          type string;
        }
      }
      leaf icmp {
        type empty;
      }
      leaf imap {
        type empty;
      }
      leaf ip {
        type empty;
      }
      leaf ipinip {
        type empty;
      }
      leaf ipsec {
        type empty;
      }
      leaf ipv6 {
        type empty;
      }
      leaf ipx {
        type empty;
      }
      leaf irc {
        type empty;
      }
      container kazaa2 {
        presence "enable kazaa version 2 matching";
        leaf file-transfer {
          type string;
        }
      }
      leaf kerberos {
        type empty;
      }
      leaf l2tp {
        type empty;
      }
      leaf ldap {
        type empty;
      }
      leaf llc2 {
        type empty;
      }
      leaf mgcp {
        type empty;
      }
      container napster {
        presence "enable napster matching";
        leaf non-std {
          type empty;
        }
      }
      leaf netbios {
        type empty;
      }
      leaf netshow {
        type empty;
      }
      leaf nfs {
        type empty;
      }
      leaf nntp {
        type empty;
      }
      leaf notes {
        type empty;
      }
      leaf novadigm {
        type empty;
      }
      leaf ntp {
        type empty;
      }
      leaf ospf {
        type empty;
      }
      leaf pad {
        type empty;
      }
      leaf pcanywhere {
        type empty;
      }
      leaf pop3 {
        type empty;
      }
      leaf pppoe {
        type empty;
      }
      leaf pptp {
        type empty;
      }
      leaf printer {
        type empty;
      }
      leaf qllc {
        type empty;
      }
      leaf rcmd {
        type empty;
      }
      leaf rip {
        type empty;
      }
      leaf rsrb {
        type empty;
      }
      leaf rsvp {
        type empty;
      }
      leaf rtcp {
        type empty;
      }
      container rtp {
        presence "enable rtp matching";
        leaf audio {
          type empty;
        }
        leaf payload-type {
          type string;
        }
        leaf video {
          type empty;
        }
      }
      leaf rtsp {
        type empty;
      }
      leaf secure-ftp {
        type empty;
      }
      leaf secure-http {
        type empty;
      }
      leaf secure-imap {
        type empty;
      }
      leaf secure-irc {
        type empty;
      }
      leaf secure-ldap {
        type empty;
      }
      leaf secure-nntp {
        type empty;
      }
      leaf secure-pop3 {
        type empty;
      }
      leaf secure-telnet {
        type empty;
      }
      leaf sip {
        type empty;
      }
      leaf skinny {
        type empty;
      }
      leaf smtp {
        type empty;
      }
      leaf snapshot {
        type empty;
      }
      leaf snmp {
        type empty;
      }
      leaf socks {
        type empty;
      }
      leaf sqlnet {
        type empty;
      }
      leaf sqlserver {
        type empty;
      }
      leaf ssh {
        type empty;
      }
      leaf streamwork {
        type empty;
      }
      leaf stun {
        type empty;
      }
      leaf sunrpc {
        type empty;
      }
      leaf syslog {
        type empty;
      }
      leaf telnet {
        type empty;
      }
      leaf tftp {
        type empty;
      }
      leaf vdolive {
        type empty;
      }
      leaf vofr {
        type empty;
      }
      leaf winmx {
        type empty;
      }
      leaf xwindows {
        type empty;
      }
    }
    leaf-list qos-group {
      // NCS patched for predictable order
      ordered-by user;
      type string;
    }
    container source-address {
      leaf-list mac {
        // NCS patched for predictable order
        ordered-by user;
        type string;
      }
    }
    leaf-list vlan {
      // NCS patched for predictable order
      ordered-by user;
      type string;
    }
  }

  grouping ncs_compliance_template_ntp-server-grouping {
    list server-list {
      // NCS patched for predictable order
      ordered-by user;
      tailf:cli-drop-node-name;
      tailf:cli-suppress-mode;
      key "ip-address";
      leaf ip-address {
        type ncs_compliance_template_host-type;
      }
      leaf key {
        type string;
      }
      leaf prefer {
        type empty;
      }
      leaf version {
        type string;
      }
    }
  }

  grouping ncs_compliance_template_line-grouping {
    container access-class {
      list acccess-list {
        // NCS patched for predictable order
        ordered-by user;
        tailf:cli-drop-node-name;
        tailf:cli-suppress-mode;
        key "direction";
        leaf direction {
          type string;
        }
        leaf access-list {
          tailf:cli-drop-node-name;
          type ncs_compliance_template_exp-acl-type;
          // NCS drop mandatory statement
        }
        leaf vrf-also {
          type empty;
        }
      }
    }
    leaf escape-character {
      type string;
    }
    leaf exec {
      type string;
      // NCS drop default statement
    }
    container exec-timeout {
      leaf minutes {
        tailf:cli-drop-node-name;
        type string;
      }
      leaf seconds {
        tailf:cli-drop-node-name;
        type string;
      }
    }
    container logging {
      container synchronous {
        presence "true";
      }
    }
    container login {
      presence "true";
      leaf local {
        type empty;
      }
      leaf authentication {
        type string;
      }
    }
    container password {
      uses ncs_compliance_template_password-07-grouping;
    }
    container privilege {
      leaf level {
        type string;
      }
    }
    container session-timeout {
      leaf session-timeout-value {
        tailf:cli-drop-node-name;
        type string;
      }
      leaf output {
        type empty;
      }
    }
    leaf stopbits {
      type string;
    }
    container telnet {
      leaf transparent {
        type empty;
      }
    }
    container transport {
      leaf-list input {
        // NCS patched for predictable order
        ordered-by user;
        type string;
      }
      leaf-list output {
        // NCS patched for predictable order
        ordered-by user;
        type string;
      }
      leaf preferred {
        type string;
      }
    }
  }

  grouping ncs_compliance_template_queue-size-grouping {
    leaf queue-size-1 {
      tailf:cli-drop-node-name;
      type string;
    }
    leaf queue-size-2 {
      tailf:cli-drop-node-name;
      type string;
    }
    leaf queue-size-3 {
      tailf:cli-drop-node-name;
      type string;
    }
    leaf queue-size-4 {
      tailf:cli-drop-node-name;
      type string;
    }
    leaf queue-size-5 {
      tailf:cli-drop-node-name;
      type string;
    }
    leaf queue-size-6 {
      tailf:cli-drop-node-name;
      type string;
    }
    leaf queue-size-7 {
      tailf:cli-drop-node-name;
      type string;
    }
    leaf queue-size-8 {
      tailf:cli-drop-node-name;
      type string;
    }
  }

  grouping ncs_compliance_template_interface-common-grouping {
    leaf description {
      type string;
    }
    container authentication {
      leaf port-control {
        type string;
      }
    }
    container mab {
      presence "true";
      leaf eap {
        type empty;
      }
    }
    container l2protocol-tunnel {
      presence "true";
      leaf cdp {
        type empty;
      }
      container drop-threshold {
        leaf packet-rate {
          tailf:cli-drop-node-name;
          type string;
        }
        leaf cdp {
          type string;
        }
        leaf stp {
          type string;
        }
        leaf vtp {
          type string;
        }
      }
      container shutdown-threshold {
        leaf packet-rate {
          tailf:cli-drop-node-name;
          type string;
        }
        leaf cdp {
          type string;
        }
        leaf stp {
          type string;
        }
        leaf vtp {
          type string;
        }
      }
      leaf stp {
        type empty;
      }
      leaf vtp {
        type empty;
      }
    }
    container encapsulation {
      container dot1Q {
        leaf vlan-id {
          tailf:cli-drop-node-name;
          type string;
        }
        leaf native {
          type empty;
        }
      }
      container isl {
        leaf vlan-id {
          tailf:cli-drop-node-name;
          type string;
        }
      }
      container ppp {
        presence "true";
      }
      container slip {
        presence "true";
      }
      container frame-relay {
        presence "true";
        leaf ietf {
          type empty;
        }
      }
    }
    container fair-queue-conf {
      tailf:cli-drop-node-name;
      // NCS drop when statement
      leaf fair-queue {
        type string;
        // NCS drop default statement
      }
    }
    container fair-queue {
      leaf incomplete {
        type empty;
      }
    }
    container flowcontrol {
      leaf receive {
        type string;
      }
      leaf send {
        type string;
      }
    }
    choice keepalive-choice {
      leaf keepalive {
        type string;
      }
      container keepalive-settings {
        tailf:cli-drop-node-name;
        container keepalive {
          leaf period {
            tailf:cli-drop-node-name;
            type string;
          }
        }
      }
    }
    container snmp {
      container ifindex {
        choice ifindex-choice {
          leaf persist {
            type empty;
          }
          leaf clear {
            type string;
            // NCS drop default statement
          }
        }
      }
      container trap {
        leaf link-status {
          type string;
          // NCS drop default statement
        }
        container link-status-capas {
          tailf:cli-drop-node-name;
          container link-status {
            container permit {
              leaf duplicates {
                type empty;
              }
            }
          }
        }
      }
    }
    container bfd {
      leaf echo {
        type empty;
      }
      container interval {
        leaf msecs {
          tailf:cli-drop-node-name;
          type string;
        }
        leaf min_rx {
          type string;
        }
        leaf multiplier {
          type string;
        }
      }
    }
    container bandwidth {
      leaf inherit {
        type empty;
      }
      leaf kilobits {
        tailf:cli-drop-node-name;
        type string;
      }
    }
    container cdp {
      leaf enable {
        type string;
        // NCS drop default statement
      }
      container tlv {
        container app {
          presence "true";
          leaf tlvtype {
            type string;
          }
          leaf value {
            type string;
          }
        }
        leaf server-location {
          type empty;
        }
        leaf location {
          type empty;
        }
      }
    }
    container dampening {
      presence "true";
      leaf dampening-time {
        tailf:cli-drop-node-name;
        type string;
      }
    }
    container hold-queue {
      leaf queue-length {
        tailf:cli-drop-node-name;
        type string;
      }
      leaf direction {
        tailf:cli-drop-node-name;
        type string;
      }
    }
    container mpls {
      container accounting {
        container experimental {
          leaf input {
            type empty;
          }
          leaf output {
            type empty;
          }
        }
      }
      container bgp {
        leaf forwarding {
          type empty;
        }
      }
      leaf ip {
        type empty;
      }
      container label {
        leaf protocol {
          type string;
        }
      }
      container ldp {
        container discovery {
          leaf transport-address {
            type ncs_compliance_template_ldp-discovery-address-type;
          }
        }
      }
      leaf mtu {
        type string;
      }
      container traffic-eng {
        leaf administrative-weight {
          type string;
        }
        leaf attribute-flags {
          type string;
        }
        container flooding {
          container thresholds {
            leaf-list down {
              // NCS patched for predictable order
              ordered-by user;
              type string;
            }
            leaf-list up {
              // NCS patched for predictable order
              ordered-by user;
              type string;
            }
          }
        }
        leaf tunnels {
          type empty;
        }
      }
    }
    choice vrf-choice {
      container ip-vrf {
        tailf:cli-drop-node-name;
        container ip {
          container vrf {
            leaf forwarding {
              type string;
            }
          }
        }
      }
      container vrf {
        leaf forwarding {
          type string;
        }
      }
    }
    container ip {
      container access-group {
        leaf access-list {
          tailf:cli-drop-node-name;
          type ncs_compliance_template_exp-acl-type;
        }
        leaf direction {
          tailf:cli-drop-node-name;
          type string;
        }
      }
      container vrf {
        leaf receive {
          type string;
        }
        leaf sitemap {
          type string;
        }
      }
      choice address-choice {
        leaf unnumbered {
          type string;
        }
        container no-address {
          tailf:cli-drop-node-name;
          leaf address {
            type string;
            // NCS drop default statement
          }
        }
        container address {
          choice address-choice {
            case fixed-case {
              container primary {
                tailf:cli-drop-node-name;
                leaf address {
                  tailf:cli-drop-node-name;
                  // NCS drop tailf-common:cli-diff-dependency statement
                  // NCS drop tailf-common:cli-diff-dependency statement
                  // NCS drop mandatory statement
                  type string;
                }
                leaf mask {
                  tailf:cli-drop-node-name;
                  // NCS drop mandatory statement
                  type string;
                }
              }
              list secondary {
                // NCS patched for predictable order
                ordered-by user;
                key "address";
                tailf:cli-drop-node-name;
                tailf:cli-suppress-mode;
                leaf address {
                  type string;
                }
                leaf mask {
                  tailf:cli-drop-node-name;
                  // NCS drop mandatory statement
                  type string;
                }
                leaf secondary {
                  type empty;
                }
              }
            }
            case dhcp-case {
              container dhcp {
                presence "IP Address negotiated via DHCP";
                container client-id {
                  // NCS drop tailf-common:cli-diff-dependency statement
                  uses ncs_compliance_template_ethernet-grouping;
                }
                leaf hostname {
                  type string;
                }
              }
            }
          }
        }
      }
      container flow {
        leaf ingress {
          type empty;
        }
        leaf egress {
          type empty;
        }
      }
      container helper-address {
        choice helper-choice {
          leaf global {
            type empty;
          }
          leaf vrf {
            // NCS drop tailf-common:cli-diff-dependency statement
            // NCS drop tailf-common:cli-diff-dependency statement
            type string;
          }
        }
        leaf address {
          tailf:cli-drop-node-name;
          type string;
        }
      }
      container ospf {
        list process-id {
          // NCS patched for predictable order
          ordered-by user;
          tailf:cli-drop-node-name;
          tailf:cli-suppress-mode;
          key "id";
          leaf id {
            type string;
          }
          leaf area {
            type string;
          }
          leaf secondaries {
            type empty;
          }
          leaf none {
            type empty;
          }
        }
        leaf network {
          type string;
        }
        container bfd {
          presence "true";
          leaf enable {
            tailf:cli-drop-node-name;
            type string;
          }
        }
        leaf cost {
          type string;
        }
      }
      container pim {
        leaf sparse-mode {
          type empty;
        }
        leaf dr-priority {
          type string;
        }
      }
      container policy {
        leaf route-map {
          type string;
        }
      }
      leaf proxy-arp {
        type string;
        // NCS drop default statement
      }
      container route-cache-conf {
        tailf:cli-drop-node-name;
        leaf route-cache {
          type string;
          // NCS drop default statement
        }
      }
      container route-cache {
        leaf cef {
          type string;
          // NCS drop default statement
        }
        leaf flow {
          type string;
          // NCS drop default statement
        }
        leaf policy {
          type string;
          // NCS drop default statement
        }
        leaf same-interface {
          type string;
          // NCS drop default statement
        }
      }
      container igmp {
        container static-group {
          list groups {
            // NCS patched for predictable order
            ordered-by user;
            tailf:cli-suppress-mode;
            tailf:cli-drop-node-name;
            key "name";
            leaf name {
              type string;
            }
          }
          list class-map {
            // NCS patched for predictable order
            ordered-by user;
            key "id";
            leaf id {
              type string;
            }
          }
        }
      }
      leaf redirects {
        type empty;
      }
      container tcp {
        leaf adjust-mss {
          type string;
        }
      }
      container virtual-reassembly {
        leaf max-reassemblies {
          type string;
        }
        leaf max-fragments {
          type string;
        }
        leaf timeout {
          type string;
        }
        leaf drop-fragments {
          type empty;
        }
        leaf in {
          type empty;
        }
      }
      container dhcp {
        container relay {
          container information {
            container check-reply {
              presence "true";
              leaf none {
                type empty;
              }
            }
            container option {
              leaf subscriber-id {
                type string;
              }
            }
            container option-insert {
              presence "true";
              leaf none {
                type empty;
              }
            }
            leaf policy-action {
              type string;
            }
            leaf trusted {
              type empty;
            }
          }
        }
        container snooping {
          container limit {
            leaf rate {
              type string;
            }
          }
          leaf trust {
            type empty;
          }
          list vlan {
            // NCS patched for predictable order
            ordered-by user;
            key "id";
            // NCS drop max-elements statement
            leaf id {
              tailf:cli-drop-node-name;
              type string;
            }
            container information {
              container option {
                container format-type {
                  container circuit-id {
                    leaf string {
                      type string;
                    }
                  }
                }
              }
            }
          }
        }
      }
      leaf mtu {
        type string;
      }
      container nat {
        leaf allow-static-host {
          type empty;
        }
        leaf enable {
          type empty;
        }
        choice nat-choice {
          leaf inside {
            type empty;
          }
          leaf outside {
            type empty;
          }
        }
      }
    }
    container ipv6 {
      container address {
        choice address-choice {
          case autoconfig-case {
            container autoconfig {
              presence "true";
              leaf default {
                type empty;
              }
            }
          }
          case manual-case {
            list prefix-list {
              // NCS patched for predictable order
              ordered-by user;
              tailf:cli-drop-node-name;
              tailf:cli-suppress-mode;
              key "prefix";
              leaf prefix {
                type ios:ncs_compliance_template_ipv6-prefix;
              }
              leaf anycast {
                type empty;
              }
              leaf eui-64 {
                type empty;
              }
            }
          }
        }
      }
      leaf enable {
        type empty;
      }
      container ospf {
        list process {
          // NCS patched for predictable order
          ordered-by user;
          tailf:cli-suppress-mode;
          tailf:cli-drop-node-name;
          key "id";
          leaf id {
            type string;
          }
          leaf area {
            type string;
          }
          leaf instance {
            type string;
          }
        }
        container bfd {
          presence "true";
          leaf disable {
            type empty;
          }
        }
        leaf cost {
          type string;
        }
        container database-filter {
          choice database {
            leaf all {
              type string;
            }
            leaf disable {
              type empty;
            }
          }
        }
        leaf dead-interval {
          type string;
        }
        container demand-circuit {
          presence "true";
          leaf disable {
            type empty;
          }
        }
        container flood-reduction {
          presence "true";
          leaf disable {
            type empty;
          }
        }
        leaf hello-interval {
          type string;
        }
        container mtu-ignore {
          presence "true";
          leaf disable {
            type empty;
          }
        }
        leaf priority {
          type string;
        }
        leaf retransmit-interval {
          type string;
        }
        leaf transmit-delay {
          type string;
        }
      }
      leaf mtu {
        type string;
      }
    }
    leaf load-interval {
      type string;
    }
    leaf max-reserved-bandwidth {
      type string;
    }
    container mls {
      container qos {
        leaf channel-consistency {
          type string;
          // NCS drop default statement
        }
        leaf trust {
          type string;
        }
        leaf vlan-based {
          type empty;
        }
      }
    }
    leaf mtu {
      type string;
    }
    container power {
      container inline {
        leaf consumption {
          type string;
        }
      }
    }
    container service-policy {
      leaf history {
        type empty;
      }
      leaf input {
        type string;
      }
      leaf output {
        type string;
      }
      container type {
        container performance-monitor {
          leaf direction {
            tailf:cli-drop-node-name;
            type string;
          }
          leaf name {
            tailf:cli-drop-node-name;
            type string;
          }
        }
      }
    }
    leaf shutdown {
      type empty;
    }
    container standby {
      leaf version {
        type string;
      }
      leaf bfd {
        type empty;
      }
      container delay {
        leaf minimum {
          type string;
        }
        leaf reload {
          type string;
        }
      }
      leaf mac-refresh {
        type string;
      }
      container use-bia {
        presence "true";
        container scope {
          leaf interface {
            type empty;
          }
        }
      }
      list standby-list {
        // NCS patched for predictable order
        ordered-by user;
        tailf:cli-drop-node-name;
        tailf:cli-suppress-mode;
        key "group-number";
        leaf group-number {
          type string;
        }
        container authentication {
          choice auth {
            leaf word {
              tailf:cli-drop-node-name;
              type string;
            }
            container md5 {
              leaf key-chain {
                type string;
              }
              container key-string {
                leaf encrypt {
                  tailf:cli-drop-node-name;
                  type string;
                }
                leaf string {
                  tailf:cli-drop-node-name;
                  type string;
                }
                leaf timeout {
                  type string;
                }
              }
            }
            leaf text {
              type string;
            }
          }
        }
        leaf follow {
          type string;
        }
        container ip {
          presence "true";
          leaf address {
            tailf:cli-drop-node-name;
            type string;
          }
          leaf secondary {
            type empty;
          }
        }
        leaf ipv6 {
          type string;
        }
        leaf mac-address {
          type string;
        }
        leaf name {
          type string;
        }
        container preempt {
          presence "true";
          container delay {
            leaf minimum {
              type string;
            }
            leaf reload {
              type string;
            }
            leaf sync {
              type string;
            }
          }
        }
        leaf priority {
          type string;
        }
        container redirect {
          container advertisement {
            container authentication {
              container md5 {
                leaf key-chain {
                  type string;
                }
                container key-string {
                  leaf encrypt {
                    tailf:cli-drop-node-name;
                    type string;
                  }
                  leaf string {
                    tailf:cli-drop-node-name;
                    type string;
                  }
                  leaf timeout {
                    type string;
                  }
                }
              }
            }
          }
          container timers {
            leaf advertisement {
              tailf:cli-drop-node-name;
              type string;
            }
            leaf holddown {
              tailf:cli-drop-node-name;
              type string;
            }
          }
          leaf unknown {
            type empty;
          }
        }
        container timers {
          container hello-interval {
            tailf:cli-drop-node-name;
            choice hello-interval-choice {
              leaf seconds {
                tailf:cli-drop-node-name;
                type string;
              }
              leaf msec {
                type string;
              }
            }
          }
          container hold-time {
            tailf:cli-drop-node-name;
            choice hold-time-choice {
              leaf seconds {
                tailf:cli-drop-node-name;
                type string;
              }
              leaf msec {
                type string;
              }
            }
          }
        }
      }
    }
    container storm-control {
      container action {
        leaf level {
          type string;
        }
      }
      container broadcast {
        leaf level {
          type string;
        }
      }
      container multicast {
        leaf level {
          type string;
        }
      }
      container unicast {
        leaf level {
          type string;
        }
      }
    }
    container wrr-queue {
      container bandwidth {
        choice bandwidth-choice {
          case a {
            leaf weight-1 {
              tailf:cli-drop-node-name;
              type string;
            }
            leaf weight-2 {
              tailf:cli-drop-node-name;
              type string;
            }
            leaf weight-3 {
              tailf:cli-drop-node-name;
              type string;
            }
            leaf weight-4 {
              tailf:cli-drop-node-name;
              type string;
            }
            leaf weight-5 {
              tailf:cli-drop-node-name;
              type string;
            }
            leaf weight-6 {
              tailf:cli-drop-node-name;
              type string;
            }
            leaf weight-7 {
              tailf:cli-drop-node-name;
              type string;
            }
          }
          case b {
            container percent {
              leaf percent-1 {
                tailf:cli-drop-node-name;
                type string;
              }
              leaf percent-2 {
                tailf:cli-drop-node-name;
                type string;
              }
              leaf percent-3 {
                tailf:cli-drop-node-name;
                type string;
              }
              leaf percent-4 {
                tailf:cli-drop-node-name;
                type string;
              }
              leaf percent-5 {
                tailf:cli-drop-node-name;
                type string;
              }
              leaf percent-6 {
                tailf:cli-drop-node-name;
                type string;
              }
              leaf percent-7 {
                tailf:cli-drop-node-name;
                type string;
              }
            }
          }
        }
      }
      list cos-map {
        // NCS patched for predictable order
        ordered-by user;
        tailf:cli-suppress-mode;
        key "queue-id threshold-id";
        leaf queue-id {
          type string;
        }
        leaf threshold-id {
          type string;
        }
        leaf-list cos-values {
          // NCS patched for predictable order
          ordered-by user;
          tailf:cli-drop-node-name;
          // NCS drop max-elements statement
          type string;
        }
      }
      container queue-limit {
        leaf weight-a {
          tailf:cli-drop-node-name;
          type string;
        }
        leaf weight-b {
          tailf:cli-drop-node-name;
          type string;
        }
        leaf weight-c {
          tailf:cli-drop-node-name;
          type string;
        }
      }
      container random-detect {
        list max-threshold {
          // NCS patched for predictable order
          ordered-by user;
          tailf:cli-suppress-mode;
          key "id";
          leaf id {
            type string;
          }
          uses ncs_compliance_template_queue-size-grouping;
        }
        list min-threshold {
          // NCS patched for predictable order
          ordered-by user;
          tailf:cli-suppress-mode;
          key "id";
          leaf id {
            type string;
          }
          uses ncs_compliance_template_queue-size-grouping;
        }
      }
      list threshold {
        // NCS patched for predictable order
        ordered-by user;
        tailf:cli-suppress-mode;
        key "id";
        leaf id {
          type string;
        }
        uses ncs_compliance_template_queue-size-grouping;
      }
    }
    container priority-queue {
      container cos-map {
        leaf id {
          tailf:cli-drop-node-name;
          type string;
        }
        leaf-list cos-values {
          // NCS patched for predictable order
          ordered-by user;
          tailf:cli-drop-node-name;
          // NCS drop max-elements statement
          type string;
        }
      }
      leaf out {
        type empty;
      }
    }
    container rep {
      container block {
        container port {
          choice port-choice {
            leaf neighbor-offset {
              tailf:cli-drop-node-name;
              type string;
            }
            leaf id {
              type string;
            }
            leaf preferred {
              type empty;
            }
          }
          leaf vlan {
            type string;
          }
        }
      }
      container preempt {
        leaf delay {
          type string;
        }
      }
      container segment {
        leaf id {
          tailf:cli-drop-node-name;
          type string;
        }
        leaf edge {
          type empty;
        }
        leaf primary {
          // NCS drop when statement
          type empty;
        }
        leaf preferred {
          type empty;
        }
      }
      container stcn {
        leaf segment {
          type string;
        }
        leaf stp {
          type empty;
        }
      }
    }
    container rcv-queue {
      list cos-map {
        // NCS patched for predictable order
        ordered-by user;
        tailf:cli-suppress-mode;
        key "queue-id threshold-id";
        leaf queue-id {
          type string;
        }
        leaf threshold-id {
          type string;
        }
        leaf-list cos-values {
          // NCS patched for predictable order
          ordered-by user;
          tailf:cli-drop-node-name;
          // NCS drop max-elements statement
          type string;
        }
      }
    }
    container udld {
      container port {
        presence "true";
        choice port-choice {
          leaf aggressive {
            type empty;
          }
          leaf disable {
            type empty;
          }
        }
      }
    }
    container peer {
      container default {
        container ip {
          container address {
            choice address-choice {
              leaf dhcp {
                type empty;
              }
              container dhcp-pool {
                presence "true";
                leaf pools {
                  tailf:cli-drop-node-name;
                  type string;
                }
              }
              container pool {
                presence "true";
                leaf pools {
                  tailf:cli-drop-node-name;
                  type string;
                }
              }
            }
          }
        }
      }
    }
  }

  grouping ncs_compliance_template_interface-ethernet-grouping {
    container carrier-delay {
      choice delay-choice {
        leaf seconds {
          tailf:cli-drop-node-name;
          type string;
        }
        leaf msec {
          type string;
        }
      }
    }
    container channel-group {
      leaf number {
        tailf:cli-drop-node-name;
        type string;
      }
      leaf mode {
        type string;
      }
    }
    leaf channel-protocol {
      type string;
    }
    container ethernet {
      container oam {
        presence "true";
        leaf max-rate {
          type string;
        }
        leaf min-rate {
          type string;
        }
        leaf mode {
          type string;
        }
        leaf timeout {
          type string;
        }
      }
    }
    leaf negotiation {
      type string;
    }
    leaf duplex {
      type string;
    }
    leaf speed {
      type string;
    }
    container xconnect {
      leaf address {
        tailf:cli-drop-node-name;
        type string;
      }
      leaf vcid {
        tailf:cli-drop-node-name;
        type string;
      }
      leaf encapsulation {
        type string;
      }
      leaf manual {
        // NCS drop when statement
        type empty;
      }
      leaf sequence {
        // NCS drop when statement
        type string;
      }
      leaf pw-class {
        type string;
      }
    }
    container pppoe {
      container enable {
        presence "true";
        leaf group {
          type string;
        }
      }
      leaf max-sessions {
        type string;
      }
    }
  }

  grouping ncs_compliance_template_interface-zone-member-grouping {
    container zone-member {
      leaf security {
        type string;
      }
    }
  }

  grouping ncs_compliance_template_interface-pointtopoint-grouping {
    container ppp {
      leaf accounting {
        type string;
      }
      container authentication {
        leaf method {
          tailf:cli-drop-node-name;
          type string;
        }
        leaf list-name {
          tailf:cli-drop-node-name;
          type string;
        }
        leaf chap {
          // NCS drop when statement
          type empty;
        }
        leaf callback {
          type empty;
        }
        leaf callin {
          type empty;
        }
        leaf callout {
          type empty;
        }
        leaf default {
          type empty;
        }
        leaf eap {
          // NCS drop when statement
          type empty;
        }
        leaf ms-chap {
          // NCS drop when statement
          type empty;
        }
        leaf ms-chap-v2 {
          // NCS drop when statement
          type empty;
        }
        leaf one-time {
          type empty;
        }
        leaf optional {
          type empty;
        }
        leaf pap {
          // NCS drop when statement
          type empty;
        }
      }
      leaf authorization {
        type string;
      }
      container ipcp {
        container dns {
          leaf primary {
            tailf:cli-drop-node-name;
            type string;
          }
        }
      }
      container multilink {
        presence "true";
        container links {
          container minimum {
            leaf minimum-value {
              tailf:cli-drop-node-name;
              type string;
            }
            leaf mandatory {
              type empty;
            }
          }
        }
        leaf group {
          type string;
        }
        container fragment {
          container delay {
            leaf delay-value {
              tailf:cli-drop-node-name;
              type string;
            }
            leaf additional-delay-value {
              tailf:cli-drop-node-name;
              type string;
            }
          }
        }
      }
    }
  }

  grouping ncs_compliance_template_crypto-pki-token-grouping {
    container removal {
      leaf timeout {
        type string;
      }
    }
  }

  grouping ncs_compliance_template_max-path-grouping {
    container max-path {
      tailf:cli-drop-node-name;
      leaf max {
        tailf:cli-drop-node-name;
        type string;
        // NCS drop default statement
      }
      leaf import {
        type string;
      }
    }
  }

  grouping ncs_compliance_template_metric-route-map-grouping {
    leaf metric {
      type string;
    }
    leaf route-map {
      type string;
    }
  }

  grouping ncs_compliance_template_route-map-metric-grouping {
    leaf route-map {
      type string;
    }
    leaf metric {
      type string;
    }
  }

  grouping ncs_compliance_template_redistribute-isis-grouping {
    choice osi-ip-choice {
      leaf ip {
        type empty;
      }
      leaf clns {
        type empty;
      }
    }
    leaf routes {
      tailf:cli-drop-node-name;
      type string;
    }
    uses ncs_compliance_template_metric-route-map-grouping;
  }

  grouping ncs_compliance_template_bgp-address-family-grouping {
    container aggregate-address {
      leaf address {
        tailf:cli-drop-node-name;
        type string;
      }
      leaf mask {
        tailf:cli-drop-node-name;
        type string;
      }
      leaf advertise-map {
        type string;
      }
      leaf as-set {
        type empty;
      }
      leaf attribute-map {
        type string;
      }
      leaf as-override {
        type empty;
      }
      leaf route-map {
        type string;
      }
      leaf summary-only {
        type empty;
      }
      leaf suppress-map {
        type string;
      }
    }
    container bgp {
      leaf router-id {
        type string;
      }
      leaf always-compare-med {
        type empty;
      }
      container bestpath {
        leaf compare-routerid {
          type empty;
        }
        container cost-community {
          leaf ignore {
            type empty;
          }
        }
        container med {
          choice med-choice {
            container confed {
              presence "Compare MED among confederation paths";
              leaf missing-at-worst {
                type empty;
              }
            }
            leaf missing-at-worst {
              type empty;
            }
          }
        }
      }
      container client-to-client {
        leaf reflection {
          type empty;
        }
      }
      leaf cluster-id {
        type string;
      }
      container confederation {
        leaf identifier {
          type string;
        }
        container peers {
          presence "Peer ASs in BGP confederation";
          leaf-list peers-as {
            // NCS patched for predictable order
            ordered-by user;
            tailf:cli-drop-node-name;
            type string;
          }
        }
      }
      container dampening {
        presence "enable bgp route-flap dampening";
        choice dampening-choice {
          leaf route-map {
            type string;
          }
          container dampen {
            tailf:cli-drop-node-name;
            leaf half-life-time {
              tailf:cli-drop-node-name;
              type string;
            }
            leaf reuse-time {
              tailf:cli-drop-node-name;
              type string;
            }
            leaf suppress-time {
              tailf:cli-drop-node-name;
              type string;
            }
            leaf max-suppress-time {
              tailf:cli-drop-node-name;
              type string;
            }
          }
        }
      }
      container default {
        choice default-choice {
          leaf ipv4-unicast {
            type string;
            // NCS drop default statement
          }
          leaf local-preference {
            type string;
          }
          leaf route-target {
            type string;
          }
        }
      }
      leaf deterministic-med {
        type empty;
      }
      leaf dmzlink-bw {
        type empty;
      }
      leaf enforce-first-as {
        type empty;
      }
      leaf fast-external-fallover {
        type empty;
      }
      container graceful-restart {
        presence "Graceful restart capability parameters";
        leaf restart-time {
          type string;
        }
        leaf stalepath-time {
          type string;
        }
      }
      list inject-map {
        // NCS patched for predictable order
        ordered-by user;
        key "name";
        leaf name {
          type string;
        }
        leaf exist-map {
          type string;
        }
        leaf copy-attributes {
          type empty;
        }
      }
      leaf log-neighbor-changes {
        type empty;
      }
      leaf maxas-limit {
        type string;
      }
      container nexthop {
        container trigger {
          leaf delay {
            type string;
          }
          leaf enable {
            type string;
            // NCS drop default statement
          }
        }
      }
      leaf redistribute-internal {
        type empty;
      }
      container regexp {
        leaf deterministic {
          type empty;
        }
      }
      leaf scan-time {
        type string;
      }
      leaf soft-reconfig-backup {
        type empty;
      }
      leaf suppress-inactive {
        type empty;
      }
      leaf update-delay {
        type string;
      }
    }
    container default-information {
      leaf originate {
        type empty;
      }
    }
    leaf default-metric {
      type string;
    }
    container distance {
      container bgp {
        leaf extern-as {
          tailf:cli-drop-node-name;
          type string;
        }
        leaf internal-as {
          tailf:cli-drop-node-name;
          type string;
        }
        leaf local {
          tailf:cli-drop-node-name;
          type string;
        }
      }
      list adm-distance {
        // NCS patched for predictable order
        ordered-by user;
        tailf:cli-drop-node-name;
        tailf:cli-suppress-mode;
        key "distance srcip wildbits";
        leaf distance {
          type string;
        }
        leaf srcip {
          type string;
        }
        leaf wildbits {
          type string;
        }
        leaf acl {
          tailf:cli-drop-node-name;
          type string;
        }
      }
    }
    list distribute-list {
      // NCS patched for predictable order
      ordered-by user;
      tailf:cli-suppress-mode;
      key "id";
      leaf id {
        type ncs_compliance_template_bgp-distribute-list-type;
      }
      choice in-out-choice {
        container in {
          presence "enable incoming routing updates";
          leaf interface {
            type string;
          }
        }
        container out {
          presence "enable outgoing routing updates";
          leaf interface {
            type string;
          }
        }
      }
    }
    container maximum-paths {
      choice max-path-choice {
        case eibgp-case {
          container eibgp {
            uses ncs_compliance_template_max-path-grouping;
          }
        }
        case ibgp-case {
          container ibgp {
            choice ibgp-choice {
              case a {
                container unequal-cost {
                  uses ncs_compliance_template_max-path-grouping;
                }
              }
              case b {
                uses ncs_compliance_template_max-path-grouping;
              }
            }
          }
        }
        case none-case {
          uses ncs_compliance_template_max-path-grouping;
        }
        case import-case {
          leaf import {
            type string;
          }
        }
      }
    }
    list neighbor {
      // NCS patched for predictable order
      ordered-by user;
      tailf:cli-suppress-mode;
      // NCS drop must statement
      key "id";
      leaf id {
        type string;
      }
      container peer-group {
        presence "true";
        leaf peer-group-name {
          tailf:cli-drop-node-name;
          type string;
        }
      }
      leaf remote-as {
        type string;
      }
      container local-as {
        presence "Specify a local-as number";
        leaf as-no {
          tailf:cli-drop-node-name;
          type string;
        }
        leaf no-prepend {
          type empty;
        }
        leaf replace-as {
          type empty;
        }
        leaf dual-as {
          type empty;
        }
      }
      leaf activate {
        type empty;
      }
      leaf advertisement-interval {
        type string;
      }
      container allowas-in {
        presence "accept as-paths";
        leaf as-number {
          tailf:cli-drop-node-name;
          type string;
        }
      }
      container as-override {
        presence "true";
        leaf disable {
          type empty;
        }
      }
      container capability {
        container orf {
          leaf-list prefix-list {
            // NCS patched for predictable order
            ordered-by user;
            // NCS drop max-elements statement
            type string;
          }
        }
      }
      container default-originate {
        presence "enable originate default route to this neighbour";
        leaf route-map {
          type string;
        }
      }
      leaf description {
        type string;
      }
      leaf disable-connected-check {
        type empty;
      }
      list distribute-list {
        // NCS patched for predictable order
        ordered-by user;
        tailf:cli-suppress-mode;
        key "inout";
        leaf inout {
          type string;
        }
        leaf accesslist {
          tailf:cli-drop-node-name;
          type ncs_compliance_template_bgp-distribute-list-type2;
          // NCS drop mandatory statement
        }
      }
      leaf dmzlink-bw {
        type empty;
      }
      container ebgp-multihop {
        presence "Allow EBGP neighbors not on directly connected networks";
        leaf max-hop {
          tailf:cli-drop-node-name;
          type string;
        }
      }
      leaf fall-over {
        type empty;
      }
      list filter-list {
        // NCS patched for predictable order
        ordered-by user;
        tailf:cli-suppress-mode;
        key "inout";
        leaf inout {
          type string;
        }
        leaf as-path-list {
          tailf:cli-drop-node-name;
          type string;
          // NCS drop mandatory statement
        }
      }
      container inherit {
        leaf peer-policy {
          type string;
        }
        leaf peer-session {
          type string;
        }
      }
      container maximum-prefix {
        leaf max-prefix-no {
          tailf:cli-drop-node-name;
          type string;
        }
        leaf threshold {
          tailf:cli-drop-node-name;
          type string;
        }
        leaf restart {
          type string;
        }
        leaf warning-only {
          type empty;
        }
      }
      leaf next-hop-self {
        type empty;
      }
      leaf next-hop-unchanged {
        type empty;
      }
      container password {
        leaf enctype {
          tailf:cli-drop-node-name;
          type string;
          // NCS drop default statement
        }
        leaf text {
          tailf:cli-drop-node-name;
          type string;
        }
      }
      list prefix-list {
        // NCS patched for predictable order
        ordered-by user;
        tailf:cli-suppress-mode;
        key "inout";
        leaf inout {
          type string;
        }
        leaf prefix-list-name {
          tailf:cli-drop-node-name;
          type string;
          // NCS drop mandatory statement
        }
      }
      leaf remove-private-as {
        type empty;
      }
      list route-map {
        // NCS patched for predictable order
        ordered-by user;
        tailf:cli-suppress-mode;
        key "inout";
        leaf inout {
          type string;
        }
        leaf route-map-name {
          tailf:cli-drop-node-name;
          type string;
          // NCS drop mandatory statement
        }
      }
      leaf route-reflector-client {
        type empty;
      }
      container send-community {
        presence "true";
        leaf send-community-where {
          tailf:cli-drop-node-name;
          type string;
        }
      }
      container send-label {
        leaf send-label-explicit {
          tailf:cli-drop-node-name;
          type string;
        }
      }
      leaf shutdown {
        type empty;
      }
      leaf soft-reconfiguration {
        type string;
      }
      container timers {
        leaf keepalive-interval {
          tailf:cli-drop-node-name;
          type string;
        }
        leaf holdtime {
          tailf:cli-drop-node-name;
          type string;
        }
        leaf minimum-neighbor-hold {
          tailf:cli-drop-node-name;
          type string;
        }
      }
      container translate-update {
        container ipv4 {
          container multicast {
            presence "Address Family modifier";
            leaf unicast {
              type empty;
            }
          }
        }
      }
      container transport {
        leaf connection-mode {
          type string;
        }
      }
      container ttl-security {
        leaf hops {
          type string;
        }
      }
      leaf unsuppress-map {
        type string;
      }
      container update-source {
        // NCS drop tailf-common:cli-diff-dependency statement
        uses ncs_compliance_template_interface-grouping;
      }
      leaf version {
        type string;
      }
      leaf weight {
        type string;
      }
      container ha-mode {
        container graceful-restart {
          presence "true";
          leaf disable {
            type empty;
          }
        }
        container sso {
          presence "true";
          leaf disable {
            type empty;
          }
        }
      }
    }
    list network {
      // NCS patched for predictable order
      ordered-by user;
      tailf:cli-suppress-mode;
      key "number";
      leaf number {
        type string;
      }
      leaf backdoor {
        type empty;
      }
      leaf mask {
        type string;
      }
      leaf route-map {
        type string;
      }
    }
    container redistribute {
      container bgp {
        leaf as-no {
          tailf:cli-drop-node-name;
          type string;
        }
        uses ncs_compliance_template_metric-route-map-grouping;
      }
      container connected {
        presence "Connected";
        uses ncs_compliance_template_metric-route-map-grouping;
      }
      container dvmrp {
        presence "Redistribution of DVMRP into BGP IPv4 Multicast";
        uses ncs_compliance_template_route-map-metric-grouping;
      }
      container eigrp {
        leaf as-no {
          tailf:cli-drop-node-name;
          type string;
        }
        uses ncs_compliance_template_metric-route-map-grouping;
      }
      container isis {
        list isis-area {
          // NCS patched for predictable order
          ordered-by user;
          tailf:cli-drop-node-name;
          key "name";
          leaf name {
            type string;
          }
          uses ncs_compliance_template_redistribute-isis-grouping;
        }
        container default {
          tailf:cli-drop-node-name;
          uses ncs_compliance_template_redistribute-isis-grouping;
        }
      }
      container iso-igrp {
        list iso-igrp-area {
          // NCS patched for predictable order
          ordered-by user;
          tailf:cli-drop-node-name;
          key "name";
          leaf name {
            type string;
          }
          uses ncs_compliance_template_route-map-metric-grouping;
        }
        container default {
          uses ncs_compliance_template_route-map-metric-grouping;
        }
      }
      container mobile {
        presence "Mobile routes";
        uses ncs_compliance_template_metric-route-map-grouping;
      }
      container odr {
        presence "On Demand stub Routes";
        uses ncs_compliance_template_metric-route-map-grouping;
      }
      list ospf {
        // NCS patched for predictable order
        ordered-by user;
        key "id";
        leaf id {
          type string;
        }
        list vrf {
          // NCS patched for predictable order
          ordered-by user;
          // NCS drop tailf-common:cli-diff-dependency statement
          // NCS drop tailf-common:cli-diff-dependency statement
          key "name";
          leaf name {
            type string;
          }
          container match;
          uses ncs_compliance_template_metric-route-map-grouping;
        }
        container non-vrf {
          tailf:cli-drop-node-name;
          container match;
          uses ncs_compliance_template_metric-route-map-grouping;
        }
      }
      container rip {
        presence "Routing Information Protocol (RIP)";
        uses ncs_compliance_template_metric-route-map-grouping;
      }
      container static {
        presence "Static routes";
        uses ncs_compliance_template_metric-route-map-grouping;
      }
    }
    leaf synchronization {
      type empty;
    }
    leaf auto-summary {
      type string;
      // NCS drop default statement
    }
    leaf table-map {
      type string;
    }
    container timers {
      leaf keepalive-interval {
        tailf:cli-drop-node-name;
        type string;
      }
      leaf holdtime {
        tailf:cli-drop-node-name;
        type string;
      }
      leaf minimum-neighbor-hold {
        tailf:cli-drop-node-name;
        type string;
      }
    }
  }

  grouping ncs_compliance_template_ospf-ospfv3-common-address-family-grouping {
    container default-information {
      container originate {
        presence "Distribute a default route";
        leaf always {
          type empty;
        }
        leaf metric {
          type string;
        }
        leaf metric-type {
          type ncs_compliance_template_ospf-metric-type;
        }
        leaf route-map {
          type string;
        }
      }
    }
    leaf default-metric {
      type string;
    }
    container discard-route {
      presence "Enable or disable discard-route installation";
      leaf external {
        type string;
      }
      leaf internal {
        type string;
      }
    }
    container distance {
      container ospf-distance {
        tailf:cli-drop-node-name;
        leaf distance {
          tailf:cli-drop-node-name;
          type string;
        }
        leaf ip {
          tailf:cli-drop-node-name;
          type string;
        }
        leaf wildcard {
          tailf:cli-drop-node-name;
          type string;
        }
        leaf acl-name {
          tailf:cli-drop-node-name;
          type ncs_compliance_template_access-list-standard-id-type;
        }
      }
      container ospf {
        leaf external {
          type string;
        }
        leaf inter-area {
          type string;
        }
        leaf intra-area {
          type string;
        }
      }
    }
    leaf maximum-paths {
      type string;
    }
    container redistribute {
      uses ncs_compliance_template_ospf-redistribute-grouping;
      container bgp {
        uses ncs_compliance_template_ospf-redistribute-bgp-grouping;
      }
      container connected {
        presence "Connected";
        uses ncs_compliance_template_ospf-redistribute-grouping;
      }
      container eigrp {
        uses ncs_compliance_template_ospf-redistribute-bgp-grouping;
      }
      container isis {
        presence "ISO IS-IS";
        choice isis-level-routes-isis-area-choice {
          leaf isis-level-routes {
            tailf:cli-drop-node-name;
            type string;
          }
          list isis-area {
            // NCS patched for predictable order
            ordered-by user;
            tailf:cli-suppress-mode;
            tailf:cli-drop-node-name;
            key "name";
            leaf name {
              type string;
            }
            uses ncs_compliance_template_ospf-redistribute-grouping;
          }
        }
        uses ncs_compliance_template_ospf-redistribute-grouping;
      }
      container iso-igrp {
        presence "IGRP for OSI networks";
        choice area-tag-route-map-choice {
          container area-tag-route-map-container {
            tailf:cli-drop-node-name;
            leaf area-tag {
              tailf:cli-drop-node-name;
              type string;
            }
            leaf route-map {
              type string;
            }
          }
          leaf route-map {
            type string;
          }
        }
        container iso-igrp-container {
          tailf:cli-drop-node-name;
          uses ncs_compliance_template_ospf-iso-igrp-redistribute-grouping;
        }
      }
      container maximum-prefix {
        leaf number {
          tailf:cli-drop-node-name;
          type string;
        }
        container threshold-warning-only-container {
          tailf:cli-drop-node-name;
          leaf threshold {
            tailf:cli-drop-node-name;
            type string;
          }
          leaf warning-only {
            type empty;
          }
        }
      }
      container mobile {
        presence "Mobile routes";
        uses ncs_compliance_template_ospf-redistribute-grouping;
      }
      container odr {
        presence "On Demand stub Routes";
        uses ncs_compliance_template_ospf-redistribute-grouping;
      }
      list ospf {
        // NCS patched for predictable order
        ordered-by user;
        tailf:cli-suppress-mode;
        key "id";
        leaf id {
          type string;
        }
        container match {
          container internal {
            presence "Redistribute OSPF internal routes";
            uses ncs_compliance_template_ospf-redistribute-match-grouping;
          }
          container external {
            presence "Redistribute OSPF external routes";
            leaf external-routes {
              tailf:cli-drop-node-name;
              type ncs_compliance_template_redist-ospf-external-type;
            }
            uses ncs_compliance_template_ospf-redistribute-match-grouping;
          }
          container nssa-external {
            presence "Redistribute OSPF NSSA external routes";
            leaf nssa-external-routes {
              tailf:cli-drop-node-name;
              type ncs_compliance_template_redist-ospf-external-type;
            }
            uses ncs_compliance_template_ospf-redistribute-match-grouping;
          }
        }
        uses ncs_compliance_template_ospf-redistribute-grouping;
        leaf vrf {
          // NCS drop tailf-common:cli-diff-dependency statement
          // NCS drop tailf-common:cli-diff-dependency statement
          type string;
        }
      }
      container rip {
        presence "Routing Information Protocol (RIP)";
        uses ncs_compliance_template_ospf-redistribute-grouping;
      }
      container static {
        presence "Static routes";
        uses ncs_compliance_template_ospf-redistribute-grouping;
      }
    }
  }

  grouping ncs_compliance_template_ospf-ospfv3-common-grouping {
    list area {
      // NCS patched for predictable order
      ordered-by user;
      tailf:cli-suppress-mode;
      key "id";
      leaf id {
        type ncs_compliance_template_ospf-area-type;
      }
      container authentication {
        presence "true";
        leaf message-digest {
          type empty;
        }
      }
      leaf default-cost {
        type string;
      }
      list filter-list {
        // NCS patched for predictable order
        ordered-by user;
        tailf:cli-suppress-mode;
        key "in-out";
        leaf prefix {
          // NCS drop mandatory statement
          type string;
        }
        leaf in-out {
          type string;
        }
      }
      container nssa {
        presence "Specify a NSSA area";
        container default-information-originate {
          presence "Originate Type 7 default into NSSA area";
          leaf metric {
            type string;
          }
          leaf metric-type {
            type ncs_compliance_template_ospf-metric-type;
          }
        }
        leaf no-ext-capability {
          type empty;
        }
        leaf no-redistribution {
          type empty;
        }
        leaf no-summary {
          type empty;
        }
        container translate {
          container type7 {
            leaf suppress-fa {
              type empty;
            }
          }
        }
      }
      list range {
        // NCS patched for predictable order
        ordered-by user;
        tailf:cli-suppress-mode;
        key "ip mask";
        leaf ip {
          type string;
        }
        leaf mask {
          type string;
        }
        choice advertise-choice {
          leaf advertise {
            type empty;
          }
          leaf not-advertise {
            type empty;
          }
        }
        leaf cost {
          type string;
        }
      }
      list sham-link {
        // NCS patched for predictable order
        ordered-by user;
        tailf:cli-suppress-mode;
        key "source dest";
        leaf source {
          type string;
        }
        leaf dest {
          type string;
        }
        leaf cost {
          type string;
        }
      }
      container stub {
        presence "Specify a stub area";
        leaf no-ext-capability {
          type empty;
        }
        leaf no-summary {
          type empty;
        }
      }
      list virtual-link {
        // NCS patched for predictable order
        ordered-by user;
        tailf:cli-suppress-mode;
        key "id";
        leaf id {
          type string;
        }
        leaf authentication {
          type empty;
        }
        container authentication-key {
          leaf auth-type {
            tailf:cli-drop-node-name;
            type string;
          }
          leaf auth-key {
            tailf:cli-drop-node-name;
            type string;
          }
        }
        leaf dead-interval {
          type string;
        }
        leaf hello-interval {
          type string;
        }
        list message-digest-key {
          // NCS patched for predictable order
          ordered-by user;
          tailf:cli-suppress-mode;
          key "id";
          leaf id {
            type string;
          }
          container md5 {
            leaf auth-type {
              tailf:cli-drop-node-name;
              type string;
            }
            leaf auth-key {
              tailf:cli-drop-node-name;
              type string;
            }
          }
        }
        leaf retransmit-interval {
          type string;
        }
        leaf transmit-delay {
          type string;
        }
      }
    }
    container auto-cost {
      presence "Calculate OSPF interface cost according to bandwidth";
      leaf reference-bandwidth {
        type string;
      }
    }
    container bfd {
      leaf all-interfaces {
        type empty;
      }
    }
    container interface-id {
      leaf snmp-if-index {
        type empty;
      }
    }
    container log-adjacency-changes {
      presence "true";
      leaf detail {
        type empty;
      }
    }
    container max-lsa {
      leaf number {
        tailf:cli-drop-node-name;
        type string;
      }
      container options {
        tailf:cli-drop-node-name;
        leaf threshold-value {
          tailf:cli-drop-node-name;
          type string;
        }
        leaf ignore-count {
          type string;
        }
        leaf ignore-time {
          type string;
        }
        leaf reset-time {
          type string;
        }
        leaf warning-only {
          type empty;
        }
      }
    }
    uses ncs_compliance_template_passive-interface-grouping;
    container queue-depth {
      container hello {
        uses ncs_compliance_template_queue-depth-grouping;
      }
      container update {
        uses ncs_compliance_template_queue-depth-grouping;
      }
    }
    container timers {
      container lsa {
        leaf arrival {
          type string;
        }
      }
      container pacing {
        leaf flood {
          type string;
        }
        leaf lsa-group {
          type string;
        }
        leaf retransmission {
          type string;
        }
      }
      container throttle {
        container lsa {
          container all {
            leaf delay {
              tailf:cli-drop-node-name;
              type string;
            }
            leaf min-delay {
              tailf:cli-drop-node-name;
              type string;
            }
            leaf max-delay {
              tailf:cli-drop-node-name;
              type string;
            }
          }
        }
        container spf {
          leaf delay {
            tailf:cli-drop-node-name;
            type string;
          }
          leaf min-delay {
            tailf:cli-drop-node-name;
            type string;
          }
          leaf max-delay {
            tailf:cli-drop-node-name;
            type string;
          }
        }
      }
    }
    leaf router-id {
      type string;
    }
  }

  grouping ncs_compliance_template_ospfv3-address-family-grouping;

  grouping ncs_compliance_template_queue-depth-grouping {
    leaf options {
      tailf:cli-drop-node-name;
      type string;
      // NCS drop default statement
    }
  }

  grouping ncs_compliance_template_ospf-redistribute-match-grouping {
    leaf metric {
      type string;
    }
    leaf subnets {
      type empty;
    }
    leaf route-map {
      type string;
    }
    leaf tag {
      type string;
    }
  }

  grouping ncs_compliance_template_ospf-iso-igrp-redistribute-grouping {
    leaf metric {
      type string;
    }
    leaf metric-type {
      type string;
    }
    leaf tag {
      type string;
    }
    leaf subnets {
      type empty;
    }
  }

  grouping ncs_compliance_template_ospf-redistribute-grouping {
    container redist-options {
      tailf:cli-drop-node-name;
      uses ncs_compliance_template_ospf-iso-igrp-redistribute-grouping;
      leaf route-map {
        type string;
      }
    }
  }

  grouping ncs_compliance_template_ospf-redistribute-bgp-grouping {
    leaf as-number {
      tailf:cli-drop-node-name;
      type string;
    }
    uses ncs_compliance_template_ospf-redistribute-grouping;
  }

  grouping ncs_compliance_template_router-rip-grouping {
    uses ncs_compliance_template_address-family-vrf-grouping;
    leaf flash-update-threshold {
      type string;
    }
    leaf input-queue {
      type string;
    }
    leaf output-delay {
      type string;
    }
    uses ncs_compliance_template_passive-interface-grouping;
    container traffic-share {
      container min {
        leaf across-interfaces {
          type empty;
        }
      }
    }
  }

  grouping ncs_compliance_template_default-redistribute-grouping {
    container connected {
      presence "Connected";
      uses ncs_compliance_template_rip-metric-route-map-grouping;
    }
    list bgp {
      // NCS patched for predictable order
      ordered-by user;
      tailf:cli-suppress-mode;
      key "as-number";
      leaf as-number {
        type string;
      }
      uses ncs_compliance_template_rip-metric-route-map-grouping;
    }
    list eigrp {
      // NCS patched for predictable order
      ordered-by user;
      tailf:cli-suppress-mode;
      key "as-number";
      leaf as-number {
        type string;
      }
      uses ncs_compliance_template_rip-metric-route-map-grouping;
    }
    container isis {
      presence "ISO IS-IS";
      list isis-area {
        // NCS patched for predictable order
        ordered-by user;
        tailf:cli-suppress-mode;
        tailf:cli-drop-node-name;
        key "name";
        leaf name {
          type string;
        }
        uses ncs_compliance_template_redist-isis-grouping;
      }
      uses ncs_compliance_template_redist-isis-grouping;
    }
    container iso-igrp {
      presence "IGRP for OSI networks";
      list isoigrp-list {
        // NCS patched for predictable order
        ordered-by user;
        tailf:cli-suppress-mode;
        tailf:cli-drop-node-name;
        key "iso-area-tag";
        leaf iso-area-tag {
          type string;
        }
        uses ncs_compliance_template_rip-iso-igrp-metric-route-map-grouping;
      }
      uses ncs_compliance_template_rip-iso-igrp-metric-route-map-grouping;
    }
    container mobile {
      presence "Mobile routes";
      uses ncs_compliance_template_rip-metric-route-map-grouping;
    }
    container odr {
      presence "On Demand stub Routes";
      uses ncs_compliance_template_rip-metric-route-map-grouping;
    }
    list ospf {
      // NCS patched for predictable order
      ordered-by user;
      tailf:cli-suppress-mode;
      key "process-id";
      leaf process-id {
        type string;
      }
      list vrf {
        // NCS patched for predictable order
        ordered-by user;
        // NCS drop tailf-common:cli-diff-dependency statement
        // NCS drop tailf-common:cli-diff-dependency statement
        key "name";
        leaf name {
          type string;
        }
      }
      container match {
        container internal {
          presence "Redistribute OSPF internal routes";
          uses ncs_compliance_template_rip-metric-route-map-grouping;
        }
        container external {
          presence "Redistribute OSPF external routes";
          leaf external-routes {
            tailf:cli-drop-node-name;
            type ncs_compliance_template_redist-ospf-external-type;
          }
          uses ncs_compliance_template_rip-metric-route-map-grouping;
        }
        container nssa-external {
          presence "Redistribute OSPF NSSA external routes";
          leaf nssa-external-routes {
            tailf:cli-drop-node-name;
            type ncs_compliance_template_redist-ospf-external-type;
          }
          uses ncs_compliance_template_rip-metric-route-map-grouping;
        }
      }
      uses ncs_compliance_template_rip-metric-route-map-grouping;
    }
    container static {
      presence "Static routes";
      uses ncs_compliance_template_rip-metric-route-map-grouping;
    }
    container rip {
      presence "Routing Information Protocol (RIP)";
      uses ncs_compliance_template_rip-metric-route-map-grouping;
    }
  }

  grouping ncs_compliance_template_distance-grouping {
    container distance {
      leaf distance-leaf {
        tailf:cli-drop-node-name;
        type string;
      }
      list distance-list {
        // NCS patched for predictable order
        ordered-by user;
        tailf:cli-suppress-mode;
        tailf:cli-drop-node-name;
        key "number ip mask";
        leaf number {
          type string;
        }
        leaf ip {
          type string;
        }
        leaf mask {
          type string;
        }
      }
    }
  }

  grouping ncs_compliance_template_offset-list-grouping {
    list offset-list {
      // NCS patched for predictable order
      ordered-by user;
      tailf:cli-suppress-mode;
      key "in-out";
      leaf in-out {
        type ncs_compliance_template_offset-list-in-out-type;
      }
      leaf offset {
        tailf:cli-drop-node-name;
        // NCS drop mandatory statement
        type string;
      }
    }
  }

  grouping ncs_compliance_template_default-router-rip-grouping {
    leaf auto-summary {
      type empty;
    }
    leaf maximum-paths {
      type string;
    }
    list neighbor {
      // NCS patched for predictable order
      ordered-by user;
      tailf:cli-suppress-mode;
      key "ip";
      leaf ip {
        type string;
      }
    }
    list network {
      // NCS patched for predictable order
      ordered-by user;
      tailf:cli-suppress-mode;
      key "ip";
      leaf ip {
        type string;
      }
    }
    leaf validate-update-source {
      type string;
      // NCS drop default statement
    }
  }

  grouping ncs_compliance_template_address-family-vrf-grouping {
    uses ncs_compliance_template_default-router-rip-grouping;
    container default-information {
      container originate {
        presence "Distribute a default route";
        leaf route-map {
          type string;
        }
      }
    }
    leaf default-metric {
      type string;
    }
    uses ncs_compliance_template_distance-grouping;
    uses ncs_compliance_template_distribute-list-grouping;
    uses ncs_compliance_template_offset-list-grouping;
    container redistribute {
      uses ncs_compliance_template_rip-metric-route-map-grouping;
      uses ncs_compliance_template_default-redistribute-grouping;
    }
    container timers {
      container basic {
        leaf updates {
          tailf:cli-drop-node-name;
          type string;
        }
        leaf invalid {
          tailf:cli-drop-node-name;
          type string;
        }
        leaf holddown {
          tailf:cli-drop-node-name;
          type string;
        }
        leaf flush {
          tailf:cli-drop-node-name;
          type string;
        }
        leaf sleep {
          tailf:cli-drop-node-name;
          type string;
        }
      }
    }
    leaf version {
      type string;
    }
  }

  grouping ncs_compliance_template_redist-isis-grouping {
    container rip-isis-redist {
      tailf:cli-drop-node-name;
      leaf isis-level-routes {
        tailf:cli-drop-node-name;
        type string;
      }
      uses ncs_compliance_template_rip-metric-route-map-grouping;
    }
  }

  grouping ncs_compliance_template_rip-metric-route-map-grouping {
    container rip-metric-route-map {
      tailf:cli-drop-node-name;
      container metric {
        choice metric-transparent-choice {
          leaf metric-value {
            tailf:cli-drop-node-name;
            type string;
          }
          leaf transparent {
            type empty;
          }
        }
      }
      leaf route-map {
        type string;
      }
    }
  }

  grouping ncs_compliance_template_rip-iso-igrp-metric-route-map-grouping {
    container rip-metric-route-map {
      tailf:cli-drop-node-name;
      leaf route-map {
        type string;
      }
      container metric {
        choice metric-transparent-choice {
          leaf metric-value {
            tailf:cli-drop-node-name;
            type string;
          }
          leaf transparent {
            type empty;
          }
        }
      }
    }
  }

  grouping ncs_compliance_template_narrow-wide-transition-grouping {
    leaf narrow-wide {
      tailf:cli-drop-node-name;
      type ncs_compliance_template_isis-level-type;
    }
    leaf transition {
      type ncs_compliance_template_isis-level-type;
    }
  }

  grouping ncs_compliance_template_spf-intervals-grouping {
    leaf interval {
      tailf:cli-drop-node-name;
      type string;
    }
    leaf initial-wait {
      tailf:cli-drop-node-name;
      type string;
    }
    leaf minimum-wait {
      tailf:cli-drop-node-name;
      type string;
    }
  }

  grouping ncs_compliance_template_authenticate-snp-grouping {
    leaf authenticate {
      type empty;
    }
    leaf snp {
      type string;
    }
  }

  grouping ncs_compliance_template_lsp-gen-interval-grouping {
    leaf interval {
      tailf:cli-drop-node-name;
      type string;
    }
    leaf initial-wait {
      tailf:cli-drop-node-name;
      type string;
    }
    leaf wait {
      tailf:cli-drop-node-name;
      type string;
    }
  }

  grouping ncs_compliance_template_set-overload-bit-suppress-grouping {
    leaf external {
      type empty;
    }
    leaf interlevel {
      type empty;
    }
  }

  grouping ncs_compliance_template_summary-address-metric-tag-grouping {
    leaf metric {
      type string;
    }
    leaf tag {
      type string;
    }
  }

  grouping ncs_compliance_template_authentication-level-grouping {
    leaf levels {
      tailf:cli-drop-node-name;
      type ncs_compliance_template_authentication-level-type;
    }
  }

  grouping ncs_compliance_template_redist-level-grouping {
    leaf levels {
      tailf:cli-drop-node-name;
      type ncs_compliance_template_isis-routes-level-type;
    }
  }

  grouping ncs_compliance_template_isis-redist-container-content-grouping {
    uses ncs_compliance_template_redist-level-grouping;
    leaf metric {
      type string;
    }
    leaf metric-type {
      type string;
    }
    leaf route-map {
      type string;
    }
  }

  grouping ncs_compliance_template_isis-redist-grouping {
    container isis-redist-container {
      tailf:cli-drop-node-name;
      uses ncs_compliance_template_isis-redist-container-content-grouping;
    }
  }

  grouping ncs_compliance_template_isis-redist-af-grouping {
    container isis-redist-af-container {
      tailf:cli-drop-node-name;
      leaf include-connected {
        type empty;
      }
      uses ncs_compliance_template_isis-redist-container-content-grouping;
    }
  }

  grouping ncs_compliance_template_isis-redist-ospf-match-grouping {
    uses ncs_compliance_template_redist-level-grouping;
    leaf metric {
      type string;
    }
    leaf route-map {
      type string;
    }
  }

  grouping ncs_compliance_template_isis-redist-clns-ip-grouping {
    uses ncs_compliance_template_isis-redist-grouping;
    container clns {
      presence "Redistribution of BGP NSAP routes";
      leaf route-map {
        type string;
      }
    }
    leaf ip {
      type empty;
    }
  }

  grouping ncs_compliance_template_isis-address-family-grouping {
    leaf adjacency-check {
      type empty;
    }
    container default-information {
      container originate {
        presence "Distribute a default route";
        leaf route-map {
          type string;
        }
      }
    }
    leaf maximum-paths {
      type string;
    }
    container metric {
      leaf default {
        tailf:cli-drop-node-name;
        type string;
      }
      leaf level-1-2 {
        tailf:cli-drop-node-name;
        type string;
      }
    }
    container prc-interval {
      leaf interval {
        tailf:cli-drop-node-name;
        type string;
      }
      leaf initial-wait {
        tailf:cli-drop-node-name;
        type string;
      }
      leaf minimum-wait {
        tailf:cli-drop-node-name;
        type string;
      }
    }
    container set-overload-bit {
      choice set-overload-bit-choice {
        container on-startup {
          choice on-startup-choice {
            container time {
              tailf:cli-drop-node-name;
              leaf time {
                tailf:cli-drop-node-name;
                type string;
              }
              leaf suppress {
                type empty;
              }
              uses ncs_compliance_template_set-overload-bit-suppress-grouping;
            }
            container wait-for-bgp {
              presence "Let BGP decide when to unset the overload bitW";
              container suppress {
                uses ncs_compliance_template_set-overload-bit-suppress-grouping;
              }
            }
          }
        }
        container suppress {
          uses ncs_compliance_template_set-overload-bit-suppress-grouping;
        }
      }
    }
    container spf-interval {
      choice spf-interval-choice {
        list level-1-2 {
          // NCS patched for predictable order
          ordered-by user;
          tailf:cli-drop-node-name;
          tailf:cli-suppress-mode;
          key "level";
          leaf level {
            type string;
          }
          uses ncs_compliance_template_spf-intervals-grouping;
        }
        container intervals {
          tailf:cli-drop-node-name;
          uses ncs_compliance_template_spf-intervals-grouping;
        }
      }
    }
    container traffic-share {
      container min {
        leaf across-interface {
          type empty;
        }
      }
    }
  }

  grouping ncs_compliance_template_isis-main-grouping {
    container isis-main-container {
      tailf:cli-drop-node-name;
      uses ncs_compliance_template_isis-address-family-grouping;
      container address-family {
        container ipv6 {
          container unicast {
            uses ncs_compliance_template_isis-address-family-grouping;
            leaf distance {
              type string;
            }
            container multi-topology {
              presence "Enable multi-topology mode";
              leaf transition {
                type empty;
              }
            }
            container redistribute {
              container bgp {
                leaf as-number {
                  tailf:cli-drop-node-name;
                  type string;
                }
                uses ncs_compliance_template_isis-redist-af-grouping;
              }
              container connected {
                presence "Connected";
                uses ncs_compliance_template_isis-redist-grouping;
              }
              list eigrp {
                // NCS patched for predictable order
                ordered-by user;
                tailf:cli-suppress-mode;
                key "as-number";
                leaf as-number {
                  tailf:cli-drop-node-name;
                  type string;
                }
                uses ncs_compliance_template_isis-redist-af-grouping;
              }
              container isis {
                leaf area-tag {
                  tailf:cli-drop-node-name;
                  type string;
                }
                container levels {
                  tailf:cli-drop-node-name;
                  leaf isis-redist-levels1 {
                    tailf:cli-drop-node-name;
                    type string;
                  }
                  leaf into {
                    type empty;
                  }
                  leaf isis-redist-levels2 {
                    tailf:cli-drop-node-name;
                    type string;
                  }
                  leaf distribute-list {
                    type string;
                  }
                }
              }
              container nemo {
                uses ncs_compliance_template_isis-redist-af-grouping;
              }
              list ospf {
                // NCS patched for predictable order
                ordered-by user;
                tailf:cli-suppress-mode;
                key "process-id";
                leaf process-id {
                  type string;
                }
                uses ncs_compliance_template_isis-redist-af-grouping;
                container match {
                  container internal {
                    presence "Redistribute OSPF internal routes";
                    uses ncs_compliance_template_isis-redist-ospf-match-grouping;
                  }
                  container external {
                    presence "Redistribute OSPF external routes";
                    leaf external-routes {
                      tailf:cli-drop-node-name;
                      type ncs_compliance_template_redist-ospf-external-type;
                    }
                    uses ncs_compliance_template_isis-redist-ospf-match-grouping;
                  }
                  container nssa-external {
                    presence "Redistribute OSPF NSSA external routes";
                    leaf nssa-external-routes {
                      tailf:cli-drop-node-name;
                      type ncs_compliance_template_redist-ospf-external-type;
                    }
                    uses ncs_compliance_template_isis-redist-ospf-match-grouping;
                  }
                }
              }
              list rip {
                // NCS patched for predictable order
                ordered-by user;
                tailf:cli-suppress-mode;
                key "process";
                leaf process {
                  type string;
                }
                uses ncs_compliance_template_isis-redist-af-grouping;
              }
              container static {
                presence "Static routes";
                uses ncs_compliance_template_isis-redist-grouping;
              }
            }
            list summary-prefix {
              // NCS patched for predictable order
              ordered-by user;
              tailf:cli-suppress-mode;
              key "prefix";
              leaf prefix {
                type string;
              }
              leaf levels {
                tailf:cli-drop-node-name;
                type string;
              }
            }
          }
        }
      }
      container advertise {
        leaf passive-only {
          type empty;
        }
      }
      container area-password {
        leaf name {
          tailf:cli-drop-node-name;
          type string;
        }
        uses ncs_compliance_template_authenticate-snp-grouping;
      }
      container authentication {
        container mode {
          container md5 {
            presence "Keyed message digest";
            uses ncs_compliance_template_authentication-level-grouping;
          }
          container text {
            presence "Clear text password";
            uses ncs_compliance_template_authentication-level-grouping;
          }
        }
        container key-chain {
          leaf name {
            tailf:cli-drop-node-name;
            type string;
          }
          uses ncs_compliance_template_authentication-level-grouping;
        }
        container send-only {
          presence "Authentication send only, receive ignore";
          uses ncs_compliance_template_authentication-level-grouping;
        }
      }
      container bfd {
        leaf all-interfaces {
          type empty;
        }
      }
      container distance {
        container clns-container {
          tailf:cli-drop-node-name;
          leaf distance {
            tailf:cli-drop-node-name;
            type string;
          }
          leaf clns {
            type empty;
          }
        }
        container ip-container {
          tailf:cli-drop-node-name;
          leaf distance {
            tailf:cli-drop-node-name;
            type string;
          }
          leaf ip {
            type empty;
          }
        }
        container acl-container {
          tailf:cli-drop-node-name;
          leaf distance {
            tailf:cli-drop-node-name;
            type string;
          }
          list acl {
            // NCS patched for predictable order
            ordered-by user;
            tailf:cli-drop-node-name;
            tailf:cli-suppress-mode;
            key "ip wildcard";
            leaf ip {
              type string;
            }
            leaf wildcard {
              type string;
            }
            leaf acl-name {
              tailf:cli-drop-node-name;
              type ncs_compliance_template_access-list-standard-id-type;
            }
          }
        }
      }
      container domain-password {
        leaf name {
          tailf:cli-drop-node-name;
          type string;
        }
        uses ncs_compliance_template_authenticate-snp-grouping;
      }
      container fast-flood {
        presence "Flood LSPs (that triggered SPF) before running SPF";
        leaf number {
          tailf:cli-drop-node-name;
          type string;
        }
      }
      container hello {
        container padding {
          presence "Pad hello PDU";
          leaf pad-type {
            tailf:cli-drop-node-name;
            type string;
          }
        }
      }
      container hostname {
        leaf dynamic {
          type empty;
        }
      }
      leaf ignore-lsp-errors {
        type empty;
      }
      container ip {
        container route {
          container priority {
            container high {
              leaf tag {
                type string;
              }
            }
          }
        }
      }
      leaf is-type {
        type string;
      }
      container ispf {
        leaf level {
          tailf:cli-drop-node-name;
          type string;
        }
        leaf number {
          tailf:cli-drop-node-name;
          type string;
        }
      }
      container log-adjacency-changes {
        presence "Log changes in adjacency state";
        leaf all {
          type empty;
        }
      }
      container lsp-full {
        container suppress {
          choice lsp-full-choince {
            container external-interlevel-container {
              tailf:cli-drop-node-name;
              leaf external {
                type empty;
              }
              leaf interlevel {
                type empty;
              }
            }
            leaf none {
              type empty;
            }
          }
        }
      }
      container lsp-gen-interval {
        choice lsp-gen-interval-choice {
          container intervals {
            tailf:cli-drop-node-name;
            uses ncs_compliance_template_lsp-gen-interval-grouping;
          }
          container intervals-levels {
            tailf:cli-drop-node-name;
            container intervals-level-1 {
              tailf:cli-drop-node-name;
              leaf level-1 {
                type empty;
              }
              uses ncs_compliance_template_lsp-gen-interval-grouping;
            }
            container intervals-level-2 {
              tailf:cli-drop-node-name;
              leaf level-2 {
                type empty;
              }
              uses ncs_compliance_template_lsp-gen-interval-grouping;
            }
          }
        }
      }
      leaf lsp-mtu {
        type string;
      }
      leaf lsp-refresh-interval {
        type string;
      }
      leaf max-area-addresses {
        type string;
      }
      leaf max-lsp-lifetime {
        type string;
      }
      container metric-style {
        choice metric-style-choice {
          container narrow {
            presence "true";
            uses ncs_compliance_template_narrow-wide-transition-grouping;
          }
          container transition {
            presence "true";
            leaf transition {
              type ncs_compliance_template_isis-level-type;
              tailf:cli-drop-node-name;
            }
          }
          container wide {
            presence "true";
            uses ncs_compliance_template_narrow-wide-transition-grouping;
          }
        }
      }
      container mpls {
        container traffic-eng {
          leaf level-1 {
            type empty;
          }
          leaf level-2 {
            type empty;
          }
          leaf multicast-intact {
            type empty;
          }
          container router-id {
            // NCS drop tailf-common:cli-diff-dependency statement
            uses ncs_compliance_template_interface-grouping;
          }
          container scanner {
            presence "Timer parameters for TE database";
            leaf interval {
              type string;
            }
            leaf max-flash {
              type string;
            }
          }
        }
      }
      list net {
        // NCS patched for predictable order
        ordered-by user;
        tailf:cli-suppress-mode;
        key "tag";
        leaf tag {
          type ncs_compliance_template_isis-net;
        }
      }
      container partition {
        leaf avoidance {
          type empty;
        }
      }
      uses ncs_compliance_template_passive-interface-grouping;
      container protocol {
        leaf shutdown {
          type empty;
        }
      }
      container redistribute {
        uses ncs_compliance_template_isis-redist-grouping;
        container bgp {
          leaf as-number {
            tailf:cli-drop-node-name;
            type string;
          }
          uses ncs_compliance_template_isis-redist-clns-ip-grouping;
        }
        container connected {
          presence "Connected";
          uses ncs_compliance_template_isis-redist-grouping;
        }
        list eigrp {
          // NCS patched for predictable order
          ordered-by user;
          tailf:cli-suppress-mode;
          key "as-number";
          leaf as-number {
            tailf:cli-drop-node-name;
            type string;
          }
          uses ncs_compliance_template_isis-redist-grouping;
        }
        container isis {
          leaf area-tag {
            tailf:cli-drop-node-name;
            type string;
          }
          container ip {
            leaf isis-redist-levels1 {
              tailf:cli-drop-node-name;
              type string;
            }
            leaf into {
              type empty;
            }
            leaf isis-redist-levels2 {
              tailf:cli-drop-node-name;
              type string;
            }
            choice isis-redist-isis-ip-choice {
              leaf distribute-list {
                type string;
              }
              leaf route-map {
                type string;
              }
            }
          }
        }
        container iso-igrp {
          presence "IGRP for OSI networks";
          choice iso-igrp-choice {
            container area-tag-route-map-container {
              tailf:cli-drop-node-name;
              leaf area-tag {
                tailf:cli-drop-node-name;
                type string;
              }
              leaf route-map {
                type string;
              }
            }
            leaf route-map {
              type string;
            }
          }
          uses ncs_compliance_template_redist-level-grouping;
          leaf metric {
            type string;
          }
          leaf metric-type {
            type string;
          }
        }
        container maximum-prefix {
          leaf number {
            tailf:cli-drop-node-name;
            type string;
          }
          leaf threshold-value {
            tailf:cli-drop-node-name;
            type string;
          }
          leaf warning-only {
            type empty;
          }
          leaf withdraw {
            type empty;
          }
        }
        container mobile {
          presence "Mobile routes";
          uses ncs_compliance_template_isis-redist-grouping;
        }
        container odr {
          presence "On Demand stub Routes";
          uses ncs_compliance_template_isis-redist-grouping;
        }
        list ospf {
          // NCS patched for predictable order
          ordered-by user;
          tailf:cli-suppress-mode;
          key "process-id";
          leaf process-id {
            type string;
          }
          uses ncs_compliance_template_isis-redist-grouping;
          container match {
            container internal {
              presence "Redistribute OSPF internal routes";
              uses ncs_compliance_template_isis-redist-ospf-match-grouping;
            }
            container external {
              presence "Redistribute OSPF external routes";
              leaf external-routes {
                tailf:cli-drop-node-name;
                type ncs_compliance_template_redist-ospf-external-type;
              }
              uses ncs_compliance_template_isis-redist-ospf-match-grouping;
            }
            container nssa-external {
              presence "Redistribute OSPF NSSA external routes";
              leaf nssa-external-routes {
                tailf:cli-drop-node-name;
                type ncs_compliance_template_redist-ospf-external-type;
              }
              uses ncs_compliance_template_isis-redist-ospf-match-grouping;
            }
          }
          leaf vrf {
            // NCS drop tailf-common:cli-diff-dependency statement
            // NCS drop tailf-common:cli-diff-dependency statement
            type string;
          }
        }
        container rip {
          presence "Routing Information Protocol (RIP)";
          uses ncs_compliance_template_isis-redist-grouping;
        }
        container static {
          presence "Static routes";
          uses ncs_compliance_template_isis-redist-clns-ip-grouping;
        }
      }
      container set-attached-bit {
        leaf route-map {
          type string;
        }
      }
      list summary-address {
        // NCS patched for predictable order
        ordered-by user;
        tailf:cli-suppress-mode;
        key "ip mask";
        leaf ip {
          type string;
        }
        leaf mask {
          type string;
        }
        container level-1 {
          presence "Summarize into level-1 area";
          uses ncs_compliance_template_summary-address-metric-tag-grouping;
        }
        container level-1-2 {
          presence "Summarize into both area and sub-domain";
          uses ncs_compliance_template_summary-address-metric-tag-grouping;
        }
        container level-2 {
          presence "Summarize into level-2 sub-domain";
          uses ncs_compliance_template_summary-address-metric-tag-grouping;
        }
        container metric-tag-container {
          tailf:cli-drop-node-name;
          uses ncs_compliance_template_summary-address-metric-tag-grouping;
        }
      }
      leaf update-queue-depth {
        type string;
      }
      container use {
        leaf external-metrics {
          type empty;
        }
      }
    }
  }

  grouping ncs_compliance_template_interface-switch-grouping {
    container switchport-conf {
      tailf:cli-drop-node-name;
      leaf switchport {
        type string;
      }
    }
    container switchport {
      container access {
        leaf vlan {
          // NCS drop tailf-common:cli-diff-dependency statement
          type string;
        }
      }
      container block {
        leaf multicast {
          type empty;
        }
        leaf unicast {
          type empty;
        }
      }
      container mode {
        choice mode-choice {
          container access {
            presence "true";
          }
          container dot1q-tunnel {
            presence "true";
          }
          leaf dynamic {
            type string;
          }
          container trunk {
            presence "true";
          }
        }
      }
      leaf nonegotiate {
        type empty;
      }
      container port-security {
        presence "true";
        container aging {
          leaf time {
            type string;
          }
          leaf type {
            type string;
          }
        }
        container mac-address {
          leaf sticky {
            type empty;
          }
          leaf hw-address {
            tailf:cli-drop-node-name;
            type string;
          }
          leaf vlan {
            type string;
          }
        }
        container maximum {
          leaf max-addresses {
            tailf:cli-drop-node-name;
            type string;
          }
          leaf vlan {
            type string;
          }
        }
        leaf violation {
          type string;
        }
      }
      container trunk {
        container allowed {
          container vlan {
            choice vlan-choice {
              leaf-list vlans {
                // NCS patched for predictable order
                ordered-by user;
                tailf:cli-range-list-syntax;
                tailf:cli-drop-node-name;
                type string;
              }
              leaf all {
                type empty;
              }
              leaf-list except {
                // NCS patched for predictable order
                ordered-by user;
                tailf:cli-range-list-syntax;
                type string;
              }
              leaf none {
                type empty;
              }
            }
          }
        }
        leaf encapsulation {
          type string;
        }
        container native {
          leaf vlan {
            type string;
          }
        }
        container pruning {
          container vlan {
            choice vlan-choice {
              leaf-list vlans {
                // NCS patched for predictable order
                ordered-by user;
                tailf:cli-range-list-syntax;
                tailf:cli-drop-node-name;
                type string;
              }
              leaf-list except {
                // NCS patched for predictable order
                ordered-by user;
                tailf:cli-range-list-syntax;
                type string;
              }
              leaf none {
                type empty;
              }
            }
          }
        }
      }
      container voice {
        leaf vlan {
          type string;
        }
        container detect {
          container cisco-phone {
            presence "true";
            leaf full-duplex {
              type empty;
            }
          }
        }
      }
      container priority {
        container extend {
          choice trust-choice {
            leaf trust {
              type empty;
            }
            leaf cos {
              type string;
            }
          }
        }
      }
      container autostate {
        leaf exclude {
          type empty;
        }
      }
      leaf protected {
        type empty;
      }
      leaf host {
        type empty;
      }
    }
    container spanning-tree {
      leaf bpdufilter {
        type string;
      }
      container bpduguard {
        choice bpduguard-choice {
          leaf disable {
            type empty;
          }
          leaf enable {
            type empty;
          }
        }
      }
      leaf cost {
        type string;
      }
      leaf guard {
        type string;
      }
      leaf link-type {
        type string;
      }
      container portfast {
        presence "true";
        leaf enable {
          tailf:cli-drop-node-name;
          type string;
        }
        leaf trunk {
          type empty;
        }
      }
      container loopguard {
        leaf default {
          type empty;
        }
      }
    }
    container srr-queue {
      container bandwidth {
        container shape {
          leaf weight1 {
            tailf:cli-drop-node-name;
            type string;
          }
          leaf weight2 {
            tailf:cli-drop-node-name;
            type string;
          }
          leaf weight3 {
            tailf:cli-drop-node-name;
            type string;
          }
          leaf weight4 {
            tailf:cli-drop-node-name;
            type string;
          }
        }
        container share {
          leaf weight1 {
            tailf:cli-drop-node-name;
            type string;
          }
          leaf weight2 {
            tailf:cli-drop-node-name;
            type string;
          }
          leaf weight3 {
            tailf:cli-drop-node-name;
            type string;
          }
          leaf weight4 {
            tailf:cli-drop-node-name;
            type string;
          }
        }
      }
    }
  }

  grouping ncs_compliance_template_password-07-grouping {
    leaf level {
      type string;
    }
    leaf type {
      tailf:cli-drop-node-name;
      type string;
    }
    leaf secret {
      tailf:cli-drop-node-name;
      type string;
    }
  }

  grouping ncs_compliance_template_aaa-authentication-dot1x-grouping {
    leaf group {
      type string;
    }
  }

  grouping ncs_template_vrf-route-target-grouping {
    list export {
      // NCS patched for predictable order
      ordered-by user;
      tailf:cli-suppress-mode;
      key "asn-ip";
      leaf asn-ip {
        type ncs_template_asn-ip-type;
      }
    }
    list import {
      // NCS patched for predictable order
      ordered-by user;
      tailf:cli-suppress-mode;
      key "asn-ip";
      leaf asn-ip {
        type ncs_template_asn-ip-type;
      }
    }
  }

  grouping ncs_template_police-action-transmit-grouping {
    leaf transmit {
      type empty;
    }
  }

  grouping ncs_template_police-action-drop-grouping {
    leaf drop {
      type empty;
    }
  }

  grouping ncs_template_police-conform-action-grouping {
    container conform-set-clp-transmit {
      tailf:cli-drop-node-name;
      container conform-action {
        leaf set-clp-transmit {
          type empty;
        }
      }
    }
    container conform-set-cos-transmit {
      tailf:cli-drop-node-name;
      container conform-action {
        leaf set-cos-transmit {
          type ncs_template_cos_value-type;
        }
      }
    }
    container conform-set-cos-transmit-table {
      tailf:cli-drop-node-name;
      container conform-action {
        leaf set-cos-transmit {
          type ncs_template_cos_value-type;
        }
        leaf table {
          type string;
        }
      }
    }
    container conform-set-discard-class-transmit {
      tailf:cli-drop-node-name;
      container conform-action {
        leaf set-discard-class-transmit {
          type string;
        }
      }
    }
    container conform-set-dscp-transmit {
      tailf:cli-drop-node-name;
      container conform-action {
        leaf set-dscp-transmit {
          type ncs_template_dscp-type;
        }
      }
    }
    container conform-set-dscp-transmit-table {
      tailf:cli-drop-node-name;
      container conform-action {
        leaf set-dscp-transmit {
          type ncs_template_dscp-type;
        }
        leaf table {
          type string;
        }
      }
    }
    container conform-set-frde-transmit {
      tailf:cli-drop-node-name;
      container conform-action {
        leaf set-frde-transmit {
          type empty;
        }
      }
    }
    container conform-set-mpls-exp-imposition-transmit {
      tailf:cli-drop-node-name;
      container conform-action {
        leaf set-mpls-exp-imposition-transmit {
          type ncs_template_exp_value-type;
        }
      }
    }
    container conform-set-mpls-exp-imposition-transmit-table {
      tailf:cli-drop-node-name;
      container conform-action {
        leaf set-mpls-exp-imposition-transmit {
          type ncs_template_exp_value-type;
        }
        leaf table {
          type string;
        }
      }
    }
    container conform-set-mpls-exp-topmost-transmit {
      tailf:cli-drop-node-name;
      container conform-action {
        leaf set-mpls-exp-topmost-transmit {
          type ncs_template_exp_value-type;
        }
      }
    }
    container conform-set-mpls-exp-topmost-transmit-table {
      tailf:cli-drop-node-name;
      container conform-action {
        leaf set-mpls-exp-topmost-transmit {
          type ncs_template_exp_value-type;
        }
        leaf table {
          type string;
        }
      }
    }
    container conform-set-prec-transmit {
      tailf:cli-drop-node-name;
      container conform-action {
        leaf set-prec-transmit {
          type ncs_template_prec_value-type;
        }
      }
    }
    container conform-set-prec-transmit-table {
      tailf:cli-drop-node-name;
      container conform-action {
        leaf set-prec-transmit {
          type ncs_template_prec_value-type;
        }
        leaf table {
          type string;
        }
      }
    }
    container conform-set-qos-transmit {
      tailf:cli-drop-node-name;
      container conform-action {
        leaf set-qos-transmit {
          type ncs_template_qos_value-type;
        }
      }
    }
    container conform-set-qos-transmit-table {
      tailf:cli-drop-node-name;
      container conform-action {
        leaf set-qos-transmit {
          type ncs_template_qos_value-type;
        }
        leaf table {
          type string;
        }
      }
    }
    container conform-transmit {
      tailf:cli-drop-node-name;
      container conform-action {
        uses ncs_template_police-action-transmit-grouping;
      }
    }
    container conform-drop {
      tailf:cli-drop-node-name;
      container conform-action {
        uses ncs_template_police-action-drop-grouping;
      }
    }
  }

  grouping ncs_template_police-exceed-action-grouping {
    container exceed-dscp {
      tailf:cli-drop-node-name;
      container exceed-action {
        leaf dscp {
          type ncs_template_dscp-type;
        }
      }
    }
    container exceed-set-clp-transmit {
      tailf:cli-drop-node-name;
      container exceed-action {
        leaf set-clp-transmit {
          type empty;
        }
      }
    }
    container exceed-set-cos-transmit {
      tailf:cli-drop-node-name;
      container exceed-action {
        leaf set-cos-transmit {
          type ncs_template_cos_value-type;
        }
      }
    }
    container exceed-set-discard-class-transmit {
      tailf:cli-drop-node-name;
      container exceed-action {
        leaf set-discard-class-transmit {
          type string;
        }
      }
    }
    container exceed-set-dscp-transmit {
      tailf:cli-drop-node-name;
      container exceed-action {
        leaf set-dscp-transmit {
          type ncs_template_dscp-type;
        }
      }
    }
    container exceed-set-frde-transmit {
      tailf:cli-drop-node-name;
      container exceed-action {
        leaf set-frde-transmit {
          type empty;
        }
      }
    }
    container exceed-set-mpls-exp-imposition-transmit {
      tailf:cli-drop-node-name;
      container exceed-action {
        leaf set-mpls-exp-imposition-transmit {
          type ncs_template_exp_value-type;
        }
      }
    }
    container exceed-set-mpls-exp-topmost-transmit {
      tailf:cli-drop-node-name;
      container exceed-action {
        leaf set-mpls-exp-topmost-transmit {
          type ncs_template_exp_value-type;
        }
      }
    }
    container exceed-set-prec-transmit {
      tailf:cli-drop-node-name;
      container exceed-action {
        leaf set-prec-transmit {
          type ncs_template_prec_value-type;
        }
      }
    }
    container exceed-set-qos-transmit {
      tailf:cli-drop-node-name;
      container exceed-action {
        leaf set-qos-transmit {
          type ncs_template_qos_value-type;
        }
      }
    }
    container exceed-transmit {
      tailf:cli-drop-node-name;
      container exceed-action {
        uses ncs_template_police-action-transmit-grouping;
      }
    }
    container exceed-drop {
      tailf:cli-drop-node-name;
      container exceed-action {
        uses ncs_template_police-action-drop-grouping;
      }
    }
  }

  grouping ncs_template_police-violate-action-grouping {
    container violate-set-clp-transmit {
      tailf:cli-drop-node-name;
      container violate-action {
        leaf set-clp-transmit {
          type empty;
        }
      }
    }
    container violate-set-cos-transmit {
      tailf:cli-drop-node-name;
      container violate-action {
        leaf set-cos-transmit {
          type ncs_template_cos_value-type;
        }
      }
    }
    container violate-set-discard-class-transmit {
      tailf:cli-drop-node-name;
      container violate-action {
        leaf set-discard-class-transmit {
          type string;
        }
      }
    }
    container violate-set-dscp-transmit {
      tailf:cli-drop-node-name;
      container violate-action {
        leaf set-dscp-transmit {
          type ncs_template_dscp-type;
        }
      }
    }
    container violate-set-frde-transmit {
      tailf:cli-drop-node-name;
      container violate-action {
        leaf set-frde-transmit {
          type empty;
        }
      }
    }
    container violate-set-mpls-exp-imposition-transmit {
      tailf:cli-drop-node-name;
      container violate-action {
        leaf set-mpls-exp-imposition-transmit {
          type ncs_template_exp_value-type;
        }
      }
    }
    container violate-set-mpls-exp-topmost-transmit {
      tailf:cli-drop-node-name;
      container violate-action {
        leaf set-mpls-exp-topmost-transmit {
          type ncs_template_exp_value-type;
        }
      }
    }
    container violate-set-prec-transmit {
      tailf:cli-drop-node-name;
      container violate-action {
        leaf set-prec-transmit {
          type ncs_template_prec_value-type;
        }
      }
    }
    container violate-set-qos-transmit {
      tailf:cli-drop-node-name;
      container violate-action {
        leaf set-qos-transmit {
          type ncs_template_qos_value-type;
        }
      }
    }
    container violate-transmit {
      tailf:cli-drop-node-name;
      container violate-action {
        uses ncs_template_police-action-transmit-grouping;
      }
    }
    container violate-drop {
      tailf:cli-drop-node-name;
      container violate-action {
        uses ncs_template_police-action-drop-grouping;
      }
    }
  }

  grouping ncs_template_police-action-grouping {
    container actions {
      tailf:cli-drop-node-name;
      uses ncs_template_police-conform-action-grouping;
      uses ncs_template_police-exceed-action-grouping;
      uses ncs_template_police-violate-action-grouping;
    }
  }

  grouping ncs_template_password-grouping {
    container password-container {
      tailf:cli-drop-node-name;
      leaf encryption {
        tailf:cli-drop-node-name;
        type string;
        // NCS drop default statement
      }
      leaf password {
        tailf:cli-drop-node-name;
        type string;
      }
    }
  }

  grouping ncs_template_distribute-list-grouping {
    container distribute-list {
      list accesslist {
        // NCS patched for predictable order
        ordered-by user;
        tailf:cli-drop-node-name;
        tailf:cli-suppress-mode;
        key "in-out";
        leaf in-out {
          type ncs_template_access-list-in-out-type;
        }
      }
      list accesslist-ifname {
        // NCS patched for predictable order
        ordered-by user;
        tailf:cli-drop-node-name;
        tailf:cli-suppress-mode;
        // NCS drop tailf-common:cli-diff-dependency statement
        key "in-out interface";
        leaf in-out {
          type ncs_template_access-list-in-out-type;
        }
        leaf interface {
          type string;
        }
      }
      list accesslist-prefix-gateway {
        // NCS patched for predictable order
        ordered-by user;
        tailf:cli-drop-node-name;
        tailf:cli-suppress-mode;
        key "in-out";
        leaf prefix-gateway {
          tailf:cli-drop-node-name;
          // NCS drop mandatory statement
          type string;
        }
        leaf name {
          tailf:cli-drop-node-name;
          // NCS drop mandatory statement
          type string;
        }
        leaf in-out {
          type ncs_template_access-list-in-out-type;
        }
      }
      list accesslist-prefix-gateway-ifname {
        // NCS patched for predictable order
        ordered-by user;
        tailf:cli-drop-node-name;
        tailf:cli-suppress-mode;
        key "in-out interface";
        leaf prefix-gateway {
          tailf:cli-drop-node-name;
          // NCS drop mandatory statement
          type string;
        }
        leaf name {
          tailf:cli-drop-node-name;
          // NCS drop mandatory statement
          type string;
        }
        leaf in-out {
          type ncs_template_access-list-in-out-type;
        }
        leaf interface {
          type string;
        }
      }
    }
  }

  grouping ncs_template_passive-interface-grouping {
    container passive-interface {
      choice passive-interface-choice {
        leaf default {
          type empty;
        }
        leaf interface {
          tailf:cli-drop-node-name;
          type string;
        }
      }
    }
    container disable {
      // NCS drop when statement
      list passive-interface {
        // NCS patched for predictable order
        ordered-by user;
        tailf:cli-suppress-mode;
        key "interface";
        leaf interface {
          tailf:cli-drop-node-name;
          type string;
        }
      }
    }
  }

  grouping ncs_template_interface-grouping {
    choice interface-choice {
      leaf Embedded-Service-Engine {
        type string;
      }
      leaf FastEthernet {
        type string;
      }
      leaf GigabitEthernet {
        type string;
      }
      leaf Loopback {
        type string;
      }
      leaf Multilink {
        type string;
      }
      leaf Port-channel {
        type string;
      }
      leaf Serial {
        type string;
      }
      leaf TenGigabitEthernet {
        type string;
      }
      leaf Virtual-Template {
        type string;
      }
      leaf Vlan {
        type string;
      }
    }
  }

  grouping ncs_template_ethernet-grouping {
    choice ethernet-choice {
      leaf FastEthernet {
        type string;
      }
      leaf GigabitEthernet {
        type string;
      }
      leaf Port-channel {
        type string;
      }
      leaf TenGigabitEthernet {
        type string;
      }
    }
  }

  grouping ncs_template_ip-community-list-standard-grouping {
    container deny {
      presence "Specify community to reject";
      list deny-list {
        // NCS patched for predictable order
        ordered-by user;
        tailf:cli-drop-node-name;
        tailf:cli-suppress-mode;
        key "expr";
        leaf expr {
          type string;
        }
      }
    }
    container permit {
      presence "Specify community to accept";
      list permit-list {
        // NCS patched for predictable order
        ordered-by user;
        tailf:cli-drop-node-name;
        tailf:cli-suppress-mode;
        key "expr";
        leaf expr {
          type string;
        }
      }
    }
  }

  grouping ncs_template_ip-community-list-expanded-grouping {
    container deny {
      presence "Specify community to reject";
      list deny-list {
        // NCS patched for predictable order
        ordered-by user;
        tailf:cli-suppress-mode;
        tailf:cli-drop-node-name;
        key "expr";
        leaf expr {
          type string;
        }
      }
    }
    container permit {
      presence "Specify community to accept";
      list permit-list {
        // NCS patched for predictable order
        ordered-by user;
        tailf:cli-suppress-mode;
        tailf:cli-drop-node-name;
        key "expr";
        leaf expr {
          type string;
        }
      }
    }
  }

  grouping ncs_template_ip-route-options-grouping {
    leaf metric {
      tailf:cli-drop-node-name;
      type string;
    }
    leaf global {
      type empty;
    }
    leaf name {
      type string;
    }
    leaf permanent {
      type empty;
    }
    leaf multicast {
      type empty;
    }
    leaf dhcp {
      type empty;
    }
    leaf tag {
      type string;
    }
    leaf track {
      type string;
    }
  }

  grouping ncs_template_ip-route-grouping {
    list ip-route-interface-forwarding-list {
      // NCS patched for predictable order
      ordered-by user;
      tailf:cli-drop-node-name;
      tailf:cli-suppress-mode;
      key "prefix mask interface forwarding-address";
      leaf prefix {
        type string;
      }
      leaf mask {
        type string;
      }
      leaf interface {
        // NCS drop tailf-common:cli-diff-dependency statement
        type string;
      }
      leaf forwarding-address {
        type string;
      }
      uses ncs_template_ip-route-options-grouping;
    }
    list ip-route-forwarding-list {
      // NCS patched for predictable order
      ordered-by user;
      tailf:cli-drop-node-name;
      tailf:cli-suppress-mode;
      key "prefix mask forwarding-address";
      leaf prefix {
        type string;
      }
      leaf mask {
        type string;
      }
      leaf forwarding-address {
        type string;
      }
      uses ncs_template_ip-route-options-grouping;
    }
    list ip-route-interface-list {
      // NCS patched for predictable order
      ordered-by user;
      tailf:cli-drop-node-name;
      tailf:cli-suppress-mode;
      key "prefix mask interface";
      leaf prefix {
        type string;
      }
      leaf mask {
        type string;
      }
      leaf interface {
        // NCS drop tailf-common:cli-diff-dependency statement
        type string;
      }
      uses ncs_template_ip-route-options-grouping;
    }
  }

  grouping ncs_template_ipv6-route-options-grouping {
    leaf distance {
      tailf:cli-drop-node-name;
      type string;
    }
    choice type-choice {
      leaf multicast {
        type empty;
      }
      leaf unicast {
        type empty;
      }
    }
    leaf tag {
      type string;
    }
  }

  grouping ncs_template_ipv6-route-entry-grouping {
    list ipv6-destination-list {
      // NCS patched for predictable order
      ordered-by user;
      tailf:cli-drop-node-name;
      tailf:cli-suppress-mode;
      key "destination";
      leaf destination {
        type string;
      }
      uses ncs_template_ipv6-route-options-grouping;
    }
  }

  grouping ncs_template_ipv6-route-grouping {
    list ipv6-route-list {
      // NCS patched for predictable order
      ordered-by user;
      tailf:cli-drop-node-name;
      tailf:cli-suppress-mode;
      key "prefix";
      leaf prefix {
        type ncs_template_ipv6-prefix;
      }
      uses ncs_template_ipv6-route-entry-grouping;
      list FastEthernet {
        // NCS patched for predictable order
        ordered-by user;
        tailf:cli-suppress-mode;
        key "name";
        leaf name {
          type string;
        }
        uses ncs_template_ipv6-route-entry-grouping;
        uses ncs_template_ipv6-route-options-grouping;
      }
      list Null {
        // NCS patched for predictable order
        ordered-by user;
        tailf:cli-suppress-mode;
        key "name";
        leaf name {
          type string;
        }
        uses ncs_template_ipv6-route-entry-grouping;
        uses ncs_template_ipv6-route-options-grouping;
      }
    }
  }

  grouping ncs_template_random-detect-grouping {
    leaf min-threshold {
      tailf:cli-drop-node-name;
      type string;
    }
    leaf max-threshold {
      tailf:cli-drop-node-name;
      type string;
    }
    leaf denominator {
      tailf:cli-drop-node-name;
      type string;
    }
  }

  grouping ncs_template_class-map-match-grouping {
    container access-group {
      leaf index {
        tailf:cli-drop-node-name;
        type string;
      }
      leaf-list name {
        // NCS patched for predictable order
        ordered-by user;
        type string;
      }
    }
    leaf any {
      type empty;
    }
    leaf-list class-map {
      // NCS patched for predictable order
      ordered-by user;
      type string;
    }
    leaf-list cos {
      // NCS patched for predictable order
      ordered-by user;
      type string;
    }
    container destination-address {
      leaf-list mac {
        // NCS patched for predictable order
        ordered-by user;
        type string;
      }
    }
    leaf-list discard-class {
      // NCS patched for predictable order
      ordered-by user;
      type string;
    }
    leaf-list dscp {
      // NCS patched for predictable order
      ordered-by user;
      type ncs_template_dscp-type;
    }
    leaf fr-de {
      type empty;
    }
    leaf-list fr-dlci {
      // NCS patched for predictable order
      ordered-by user;
      type string;
    }
    leaf-list input-interface {
      // NCS patched for predictable order
      ordered-by user;
      type string;
    }
    container ip {
      leaf-list dscp {
        // NCS patched for predictable order
        ordered-by user;
        type ncs_template_dscp-type;
      }
      leaf-list precedence {
        // NCS patched for predictable order
        ordered-by user;
        type ncs_template_precedence-type;
      }
      list rtp {
        // NCS patched for predictable order
        ordered-by user;
        key "port1 port2";
        leaf port1 {
          type string;
        }
        leaf port2 {
          type string;
        }
      }
    }
    container mpls {
      container experimental {
        leaf-list topmost {
          // NCS patched for predictable order
          ordered-by user;
          type string;
        }
      }
    }
    container packet {
      container length {
        leaf max {
          type string;
        }
        leaf min {
          type string;
        }
      }
    }
    leaf-list precedence {
      // NCS patched for predictable order
      ordered-by user;
      type ncs_template_precedence-type;
    }
    container protocol {
      leaf x802-11-iapp {
        tailf:alt-name "802-11-iapp";
        type empty;
      }
      leaf ace-svr {
        type empty;
      }
      leaf aol {
        type empty;
      }
      leaf appleqtc {
        type empty;
      }
      leaf biff {
        type empty;
      }
      leaf bittorrent {
        type empty;
      }
      leaf bootpc {
        type empty;
      }
      leaf bootps {
        type empty;
      }
      leaf cddbp {
        type empty;
      }
      leaf cifs {
        type empty;
      }
      leaf cisco-fna {
        type empty;
      }
      leaf cisco-net-mgmt {
        type empty;
      }
      leaf cisco-svcs {
        type empty;
      }
      leaf cisco-sys {
        type empty;
      }
      leaf cisco-tdp {
        type empty;
      }
      leaf cisco-tna {
        type empty;
      }
      leaf citriximaclient {
        type empty;
      }
      leaf clp {
        type empty;
      }
      leaf creativepartnr {
        type empty;
      }
      leaf creativeserver {
        type empty;
      }
      leaf daytime {
        type empty;
      }
      leaf dbase {
        type empty;
      }
      leaf dbcontrol_agent {
        type empty;
      }
      leaf ddns-v3 {
        type empty;
      }
      leaf dhcp-failover {
        type empty;
      }
      leaf directconnect {
        type empty;
      }
      leaf discard {
        type empty;
      }
      leaf dnsix {
        type empty;
      }
      leaf echo {
        type empty;
      }
      leaf entrust-svc-hdlr {
        type empty;
      }
      leaf entrust-svcs {
        type empty;
      }
      leaf exec {
        type empty;
      }
      leaf fcip-port {
        type empty;
      }
      leaf ftps {
        type empty;
      }
      leaf gdoi {
        type empty;
      }
      leaf giop {
        type empty;
      }
      leaf gtpv0 {
        type empty;
      }
      leaf gtpv1 {
        type empty;
      }
      leaf h225ras {
        type empty;
      }
      leaf h323callsigalt {
        type empty;
      }
      leaf hp-alarm-mgr {
        type empty;
      }
      leaf hp-collector {
        type empty;
      }
      leaf hp-managed-node {
        type empty;
      }
      leaf hsrp {
        type empty;
      }
      leaf https {
        type empty;
      }
      leaf ica {
        type empty;
      }
      leaf icabrowser {
        type empty;
      }
      leaf ident {
        type empty;
      }
      leaf igmpv3lite {
        type empty;
      }
      leaf imap3 {
        type empty;
      }
      leaf imaps {
        type empty;
      }
      leaf ipass {
        type empty;
      }
      leaf ipsec-msft {
        type empty;
      }
      leaf irc-serv {
        type empty;
      }
      leaf ircs {
        type empty;
      }
      leaf ircu {
        type empty;
      }
      leaf isakmp {
        type empty;
      }
      leaf iscsi {
        type empty;
      }
      leaf iscsi-target {
        type empty;
      }
      leaf kermit {
        type empty;
      }
      leaf ldap-admin {
        type empty;
      }
      leaf ldaps {
        type empty;
      }
      leaf login {
        type empty;
      }
      leaf lotusmtap {
        type empty;
      }
      leaf lotusnote {
        type empty;
      }
      leaf microsoft-ds {
        type empty;
      }
      leaf ms-cluster-net {
        type empty;
      }
      leaf ms-dotnetster {
        type empty;
      }
      leaf ms-sna {
        type empty;
      }
      leaf ms-sql {
        type empty;
      }
      leaf ms-sql-m {
        type empty;
      }
      leaf msexch-routing {
        type empty;
      }
      leaf msnmsgr {
        type empty;
      }
      leaf msrpc {
        type empty;
      }
      leaf mysql {
        type empty;
      }
      leaf n2h2server {
        type empty;
      }
      leaf ncp {
        type empty;
      }
      leaf net8-cman {
        type empty;
      }
      leaf netbios-dgm {
        type empty;
      }
      leaf netbios-ns {
        type empty;
      }
      leaf netbios-ssn {
        type empty;
      }
      leaf netstat {
        type empty;
      }
      leaf oem-agent {
        type empty;
      }
      leaf oracle {
        type empty;
      }
      leaf oracle-em-vp {
        type empty;
      }
      leaf oraclenames {
        type empty;
      }
      leaf orasrv {
        type empty;
      }
      leaf pcanywheredata {
        type empty;
      }
      leaf pcanywherestat {
        type empty;
      }
      leaf pop3s {
        type empty;
      }
      leaf pwdgen {
        type empty;
      }
      leaf qmtp {
        type empty;
      }
      leaf r-winsock {
        type empty;
      }
      leaf radius {
        type empty;
      }
      leaf rdb-dbs-disp {
        type empty;
      }
      leaf realmedia {
        type empty;
      }
      leaf realsecure {
        type empty;
      }
      leaf router {
        type empty;
      }
      leaf rsvp-encap {
        type empty;
      }
      leaf rsvp_tunnel {
        type empty;
      }
      leaf rtc-pm-port {
        type empty;
      }
      leaf rtelnet {
        type empty;
      }
      leaf send {
        type empty;
      }
      leaf shell {
        type empty;
      }
      leaf sip-tls {
        type empty;
      }
      leaf sms {
        type empty;
      }
      leaf snmptrap {
        type empty;
      }
      leaf sql-net {
        type empty;
      }
      leaf sqlserv {
        type empty;
      }
      leaf sqlsrv {
        type empty;
      }
      leaf sshell {
        type empty;
      }
      leaf ssp {
        type empty;
      }
      leaf syslog-conn {
        type empty;
      }
      leaf tacacs {
        type empty;
      }
      leaf tacacs-ds {
        type empty;
      }
      leaf tarantella {
        type empty;
      }
      leaf tcp {
        type empty;
      }
      leaf telnets {
        type empty;
      }
      leaf time {
        type empty;
      }
      leaf timed {
        type empty;
      }
      leaf tr-rsrb {
        type empty;
      }
      leaf ttc {
        type empty;
      }
      leaf udp {
        type empty;
      }
      leaf uucp {
        type empty;
      }
      leaf vqp {
        type empty;
      }
      leaf webster {
        type empty;
      }
      leaf who {
        type empty;
      }
      leaf wins {
        type empty;
      }
      leaf x11 {
        type empty;
      }
      leaf xdmcp {
        type empty;
      }
      leaf ymsgr {
        type empty;
      }
      leaf aarp {
        type empty;
      }
      leaf appletalk {
        type empty;
      }
      leaf arp {
        type empty;
      }
      leaf bgp {
        type empty;
      }
      leaf bridge {
        type empty;
      }
      leaf bstun {
        type empty;
      }
      leaf cdp {
        type empty;
      }
      container citrix {
        presence "enable citrix system protocol matching";
        leaf ica-tag {
          type string;
        }
      }
      leaf clns {
        type empty;
      }
      leaf clns_es {
        type empty;
      }
      leaf clns_is {
        type empty;
      }
      leaf cmns {
        type empty;
      }
      leaf compressedtcp {
        type empty;
      }
      leaf cuseeme {
        type empty;
      }
      leaf decnet {
        type empty;
      }
      leaf decnet_node {
        type empty;
      }
      leaf decnet_router-l1 {
        type empty;
      }
      leaf decnet_router-l2 {
        type empty;
      }
      leaf dhcp {
        type empty;
      }
      leaf dlsw {
        type empty;
      }
      leaf dns {
        type empty;
      }
      leaf edonkey {
        type empty;
      }
      leaf egp {
        type empty;
      }
      leaf eigrp {
        type empty;
      }
      leaf exchange {
        type empty;
      }
      container fasttrack {
        presence "enable fasttrack matching";
        leaf file-transfer {
          type string;
        }
      }
      leaf finger {
        type empty;
      }
      leaf ftp {
        type empty;
      }
      container gnutella {
        presence "enable gnutella matching";
        leaf file-transfer {
          type string;
        }
      }
      leaf gopher {
        type empty;
      }
      leaf gre {
        type empty;
      }
      leaf h323 {
        type empty;
      }
      container http {
        presence "enable http traffic matching";
        leaf c-header-field {
          type string;
        }
        leaf host {
          type string;
        }
        leaf mime {
          type string;
        }
        leaf s-header-field {
          type string;
        }
        leaf url {
          type string;
        }
      }
      leaf icmp {
        type empty;
      }
      leaf imap {
        type empty;
      }
      leaf ip {
        type empty;
      }
      leaf ipinip {
        type empty;
      }
      leaf ipsec {
        type empty;
      }
      leaf ipv6 {
        type empty;
      }
      leaf ipx {
        type empty;
      }
      leaf irc {
        type empty;
      }
      container kazaa2 {
        presence "enable kazaa version 2 matching";
        leaf file-transfer {
          type string;
        }
      }
      leaf kerberos {
        type empty;
      }
      leaf l2tp {
        type empty;
      }
      leaf ldap {
        type empty;
      }
      leaf llc2 {
        type empty;
      }
      leaf mgcp {
        type empty;
      }
      container napster {
        presence "enable napster matching";
        leaf non-std {
          type empty;
        }
      }
      leaf netbios {
        type empty;
      }
      leaf netshow {
        type empty;
      }
      leaf nfs {
        type empty;
      }
      leaf nntp {
        type empty;
      }
      leaf notes {
        type empty;
      }
      leaf novadigm {
        type empty;
      }
      leaf ntp {
        type empty;
      }
      leaf ospf {
        type empty;
      }
      leaf pad {
        type empty;
      }
      leaf pcanywhere {
        type empty;
      }
      leaf pop3 {
        type empty;
      }
      leaf pppoe {
        type empty;
      }
      leaf pptp {
        type empty;
      }
      leaf printer {
        type empty;
      }
      leaf qllc {
        type empty;
      }
      leaf rcmd {
        type empty;
      }
      leaf rip {
        type empty;
      }
      leaf rsrb {
        type empty;
      }
      leaf rsvp {
        type empty;
      }
      leaf rtcp {
        type empty;
      }
      container rtp {
        presence "enable rtp matching";
        leaf audio {
          type empty;
        }
        leaf payload-type {
          type string;
        }
        leaf video {
          type empty;
        }
      }
      leaf rtsp {
        type empty;
      }
      leaf secure-ftp {
        type empty;
      }
      leaf secure-http {
        type empty;
      }
      leaf secure-imap {
        type empty;
      }
      leaf secure-irc {
        type empty;
      }
      leaf secure-ldap {
        type empty;
      }
      leaf secure-nntp {
        type empty;
      }
      leaf secure-pop3 {
        type empty;
      }
      leaf secure-telnet {
        type empty;
      }
      leaf sip {
        type empty;
      }
      leaf skinny {
        type empty;
      }
      leaf smtp {
        type empty;
      }
      leaf snapshot {
        type empty;
      }
      leaf snmp {
        type empty;
      }
      leaf socks {
        type empty;
      }
      leaf sqlnet {
        type empty;
      }
      leaf sqlserver {
        type empty;
      }
      leaf ssh {
        type empty;
      }
      leaf streamwork {
        type empty;
      }
      leaf stun {
        type empty;
      }
      leaf sunrpc {
        type empty;
      }
      leaf syslog {
        type empty;
      }
      leaf telnet {
        type empty;
      }
      leaf tftp {
        type empty;
      }
      leaf vdolive {
        type empty;
      }
      leaf vofr {
        type empty;
      }
      leaf winmx {
        type empty;
      }
      leaf xwindows {
        type empty;
      }
    }
    leaf-list qos-group {
      // NCS patched for predictable order
      ordered-by user;
      type string;
    }
    container source-address {
      leaf-list mac {
        // NCS patched for predictable order
        ordered-by user;
        type string;
      }
    }
    leaf-list vlan {
      // NCS patched for predictable order
      ordered-by user;
      type string;
    }
  }

  grouping ncs_template_ntp-server-grouping {
    list server-list {
      // NCS patched for predictable order
      ordered-by user;
      tailf:cli-drop-node-name;
      tailf:cli-suppress-mode;
      key "ip-address";
      leaf ip-address {
        type ncs_template_host-type;
      }
      leaf key {
        type string;
      }
      leaf prefer {
        type empty;
      }
      leaf version {
        type string;
      }
    }
  }

  grouping ncs_template_line-grouping {
    container access-class {
      list acccess-list {
        // NCS patched for predictable order
        ordered-by user;
        tailf:cli-drop-node-name;
        tailf:cli-suppress-mode;
        key "direction";
        leaf direction {
          type string;
        }
        leaf access-list {
          tailf:cli-drop-node-name;
          type ncs_template_exp-acl-type;
          // NCS drop mandatory statement
        }
        leaf vrf-also {
          type empty;
        }
      }
    }
    leaf escape-character {
      type string;
    }
    leaf exec {
      type string;
      // NCS drop default statement
    }
    container exec-timeout {
      leaf minutes {
        tailf:cli-drop-node-name;
        type string;
      }
      leaf seconds {
        tailf:cli-drop-node-name;
        type string;
      }
    }
    container logging {
      container synchronous {
        presence "true";
      }
    }
    container login {
      presence "true";
      leaf local {
        type empty;
      }
      leaf authentication {
        type string;
      }
    }
    container password {
      uses ncs_template_password-07-grouping;
    }
    container privilege {
      leaf level {
        type string;
      }
    }
    container session-timeout {
      leaf session-timeout-value {
        tailf:cli-drop-node-name;
        type string;
      }
      leaf output {
        type empty;
      }
    }
    leaf stopbits {
      type string;
    }
    container telnet {
      leaf transparent {
        type empty;
      }
    }
    container transport {
      leaf-list input {
        // NCS patched for predictable order
        ordered-by user;
        type string;
      }
      leaf-list output {
        // NCS patched for predictable order
        ordered-by user;
        type string;
      }
      leaf preferred {
        type string;
      }
    }
  }

  grouping ncs_template_queue-size-grouping {
    leaf queue-size-1 {
      tailf:cli-drop-node-name;
      type string;
    }
    leaf queue-size-2 {
      tailf:cli-drop-node-name;
      type string;
    }
    leaf queue-size-3 {
      tailf:cli-drop-node-name;
      type string;
    }
    leaf queue-size-4 {
      tailf:cli-drop-node-name;
      type string;
    }
    leaf queue-size-5 {
      tailf:cli-drop-node-name;
      type string;
    }
    leaf queue-size-6 {
      tailf:cli-drop-node-name;
      type string;
    }
    leaf queue-size-7 {
      tailf:cli-drop-node-name;
      type string;
    }
    leaf queue-size-8 {
      tailf:cli-drop-node-name;
      type string;
    }
  }

  grouping ncs_template_interface-common-grouping {
    leaf description {
      type string;
    }
    container authentication {
      leaf port-control {
        type string;
      }
    }
    container mab {
      presence "true";
      leaf eap {
        type empty;
      }
    }
    container l2protocol-tunnel {
      presence "true";
      leaf cdp {
        type empty;
      }
      container drop-threshold {
        leaf packet-rate {
          tailf:cli-drop-node-name;
          type string;
        }
        leaf cdp {
          type string;
        }
        leaf stp {
          type string;
        }
        leaf vtp {
          type string;
        }
      }
      container shutdown-threshold {
        leaf packet-rate {
          tailf:cli-drop-node-name;
          type string;
        }
        leaf cdp {
          type string;
        }
        leaf stp {
          type string;
        }
        leaf vtp {
          type string;
        }
      }
      leaf stp {
        type empty;
      }
      leaf vtp {
        type empty;
      }
    }
    container encapsulation {
      container dot1Q {
        leaf vlan-id {
          tailf:cli-drop-node-name;
          type string;
        }
        leaf native {
          type empty;
        }
      }
      container isl {
        leaf vlan-id {
          tailf:cli-drop-node-name;
          type string;
        }
      }
      container ppp {
        presence "true";
      }
      container slip {
        presence "true";
      }
      container frame-relay {
        presence "true";
        leaf ietf {
          type empty;
        }
      }
    }
    container fair-queue-conf {
      tailf:cli-drop-node-name;
      // NCS drop when statement
      leaf fair-queue {
        type string;
        // NCS drop default statement
      }
    }
    container fair-queue {
      leaf incomplete {
        type empty;
      }
    }
    container flowcontrol {
      leaf receive {
        type string;
      }
      leaf send {
        type string;
      }
    }
    choice keepalive-choice {
      leaf keepalive {
        type string;
      }
      container keepalive-settings {
        tailf:cli-drop-node-name;
        container keepalive {
          leaf period {
            tailf:cli-drop-node-name;
            type string;
          }
        }
      }
    }
    container snmp {
      container ifindex {
        choice ifindex-choice {
          leaf persist {
            type empty;
          }
          leaf clear {
            type string;
            // NCS drop default statement
          }
        }
      }
      container trap {
        leaf link-status {
          type string;
          // NCS drop default statement
        }
        container link-status-capas {
          tailf:cli-drop-node-name;
          container link-status {
            container permit {
              leaf duplicates {
                type empty;
              }
            }
          }
        }
      }
    }
    container bfd {
      leaf echo {
        type empty;
      }
      container interval {
        leaf msecs {
          tailf:cli-drop-node-name;
          type string;
        }
        leaf min_rx {
          type string;
        }
        leaf multiplier {
          type string;
        }
      }
    }
    container bandwidth {
      leaf inherit {
        type empty;
      }
      leaf kilobits {
        tailf:cli-drop-node-name;
        type string;
      }
    }
    container cdp {
      leaf enable {
        type string;
        // NCS drop default statement
      }
      container tlv {
        container app {
          presence "true";
          leaf tlvtype {
            type string;
          }
          leaf value {
            type string;
          }
        }
        leaf server-location {
          type empty;
        }
        leaf location {
          type empty;
        }
      }
    }
    container dampening {
      presence "true";
      leaf dampening-time {
        tailf:cli-drop-node-name;
        type string;
      }
    }
    container hold-queue {
      leaf queue-length {
        tailf:cli-drop-node-name;
        type string;
      }
      leaf direction {
        tailf:cli-drop-node-name;
        type string;
      }
    }
    container mpls {
      container accounting {
        container experimental {
          leaf input {
            type empty;
          }
          leaf output {
            type empty;
          }
        }
      }
      container bgp {
        leaf forwarding {
          type empty;
        }
      }
      leaf ip {
        type empty;
      }
      container label {
        leaf protocol {
          type string;
        }
      }
      container ldp {
        container discovery {
          leaf transport-address {
            type ncs_template_ldp-discovery-address-type;
          }
        }
      }
      leaf mtu {
        type string;
      }
      container traffic-eng {
        leaf administrative-weight {
          type string;
        }
        leaf attribute-flags {
          type string;
        }
        container flooding {
          container thresholds {
            leaf-list down {
              // NCS patched for predictable order
              ordered-by user;
              type string;
            }
            leaf-list up {
              // NCS patched for predictable order
              ordered-by user;
              type string;
            }
          }
        }
        leaf tunnels {
          type empty;
        }
      }
    }
    choice vrf-choice {
      container ip-vrf {
        tailf:cli-drop-node-name;
        container ip {
          container vrf {
            leaf forwarding {
              type string;
            }
          }
        }
      }
      container vrf {
        leaf forwarding {
          type string;
        }
      }
    }
    container ip {
      container access-group {
        leaf access-list {
          tailf:cli-drop-node-name;
          type ncs_template_exp-acl-type;
        }
        leaf direction {
          tailf:cli-drop-node-name;
          type string;
        }
      }
      container vrf {
        leaf receive {
          type string;
        }
        leaf sitemap {
          type string;
        }
      }
      choice address-choice {
        leaf unnumbered {
          type string;
        }
        container no-address {
          tailf:cli-drop-node-name;
          leaf address {
            type string;
            // NCS drop default statement
          }
        }
        container address {
          choice address-choice {
            case fixed-case {
              container primary {
                tailf:cli-drop-node-name;
                leaf address {
                  tailf:cli-drop-node-name;
                  // NCS drop tailf-common:cli-diff-dependency statement
                  // NCS drop tailf-common:cli-diff-dependency statement
                  // NCS drop mandatory statement
                  type string;
                }
                leaf mask {
                  tailf:cli-drop-node-name;
                  // NCS drop mandatory statement
                  type string;
                }
              }
              list secondary {
                // NCS patched for predictable order
                ordered-by user;
                key "address";
                tailf:cli-drop-node-name;
                tailf:cli-suppress-mode;
                leaf address {
                  type string;
                }
                leaf mask {
                  tailf:cli-drop-node-name;
                  // NCS drop mandatory statement
                  type string;
                }
                leaf secondary {
                  type empty;
                }
              }
            }
            case dhcp-case {
              container dhcp {
                presence "IP Address negotiated via DHCP";
                container client-id {
                  // NCS drop tailf-common:cli-diff-dependency statement
                  uses ncs_template_ethernet-grouping;
                }
                leaf hostname {
                  type string;
                }
              }
            }
          }
        }
      }
      container flow {
        leaf ingress {
          type empty;
        }
        leaf egress {
          type empty;
        }
      }
      container helper-address {
        choice helper-choice {
          leaf global {
            type empty;
          }
          leaf vrf {
            // NCS drop tailf-common:cli-diff-dependency statement
            // NCS drop tailf-common:cli-diff-dependency statement
            type string;
          }
        }
        leaf address {
          tailf:cli-drop-node-name;
          type string;
        }
      }
      container ospf {
        list process-id {
          // NCS patched for predictable order
          ordered-by user;
          tailf:cli-drop-node-name;
          tailf:cli-suppress-mode;
          key "id";
          leaf id {
            type string;
          }
          leaf area {
            type string;
          }
          leaf secondaries {
            type empty;
          }
          leaf none {
            type empty;
          }
        }
        leaf network {
          type string;
        }
        container bfd {
          presence "true";
          leaf enable {
            tailf:cli-drop-node-name;
            type string;
          }
        }
        leaf cost {
          type string;
        }
      }
      container pim {
        leaf sparse-mode {
          type empty;
        }
        leaf dr-priority {
          type string;
        }
      }
      container policy {
        leaf route-map {
          type string;
        }
      }
      leaf proxy-arp {
        type string;
        // NCS drop default statement
      }
      container route-cache-conf {
        tailf:cli-drop-node-name;
        leaf route-cache {
          type string;
          // NCS drop default statement
        }
      }
      container route-cache {
        leaf cef {
          type string;
          // NCS drop default statement
        }
        leaf flow {
          type string;
          // NCS drop default statement
        }
        leaf policy {
          type string;
          // NCS drop default statement
        }
        leaf same-interface {
          type string;
          // NCS drop default statement
        }
      }
      container igmp {
        container static-group {
          list groups {
            // NCS patched for predictable order
            ordered-by user;
            tailf:cli-suppress-mode;
            tailf:cli-drop-node-name;
            key "name";
            leaf name {
              type string;
            }
          }
          list class-map {
            // NCS patched for predictable order
            ordered-by user;
            key "id";
            leaf id {
              type string;
            }
          }
        }
      }
      leaf redirects {
        type empty;
      }
      container tcp {
        leaf adjust-mss {
          type string;
        }
      }
      container virtual-reassembly {
        leaf max-reassemblies {
          type string;
        }
        leaf max-fragments {
          type string;
        }
        leaf timeout {
          type string;
        }
        leaf drop-fragments {
          type empty;
        }
        leaf in {
          type empty;
        }
      }
      container dhcp {
        container relay {
          container information {
            container check-reply {
              presence "true";
              leaf none {
                type empty;
              }
            }
            container option {
              leaf subscriber-id {
                type string;
              }
            }
            container option-insert {
              presence "true";
              leaf none {
                type empty;
              }
            }
            leaf policy-action {
              type string;
            }
            leaf trusted {
              type empty;
            }
          }
        }
        container snooping {
          container limit {
            leaf rate {
              type string;
            }
          }
          leaf trust {
            type empty;
          }
          list vlan {
            // NCS patched for predictable order
            ordered-by user;
            key "id";
            // NCS drop max-elements statement
            leaf id {
              tailf:cli-drop-node-name;
              type string;
            }
            container information {
              container option {
                container format-type {
                  container circuit-id {
                    leaf string {
                      type string;
                    }
                  }
                }
              }
            }
          }
        }
      }
      leaf mtu {
        type string;
      }
      container nat {
        leaf allow-static-host {
          type empty;
        }
        leaf enable {
          type empty;
        }
        choice nat-choice {
          leaf inside {
            type empty;
          }
          leaf outside {
            type empty;
          }
        }
      }
    }
    container ipv6 {
      container address {
        choice address-choice {
          case autoconfig-case {
            container autoconfig {
              presence "true";
              leaf default {
                type empty;
              }
            }
          }
          case manual-case {
            list prefix-list {
              // NCS patched for predictable order
              ordered-by user;
              tailf:cli-drop-node-name;
              tailf:cli-suppress-mode;
              key "prefix";
              leaf prefix {
                type ios:ncs_template_ipv6-prefix;
              }
              leaf anycast {
                type empty;
              }
              leaf eui-64 {
                type empty;
              }
            }
          }
        }
      }
      leaf enable {
        type empty;
      }
      container ospf {
        list process {
          // NCS patched for predictable order
          ordered-by user;
          tailf:cli-suppress-mode;
          tailf:cli-drop-node-name;
          key "id";
          leaf id {
            type string;
          }
          leaf area {
            type string;
          }
          leaf instance {
            type string;
          }
        }
        container bfd {
          presence "true";
          leaf disable {
            type empty;
          }
        }
        leaf cost {
          type string;
        }
        container database-filter {
          choice database {
            leaf all {
              type string;
            }
            leaf disable {
              type empty;
            }
          }
        }
        leaf dead-interval {
          type string;
        }
        container demand-circuit {
          presence "true";
          leaf disable {
            type empty;
          }
        }
        container flood-reduction {
          presence "true";
          leaf disable {
            type empty;
          }
        }
        leaf hello-interval {
          type string;
        }
        container mtu-ignore {
          presence "true";
          leaf disable {
            type empty;
          }
        }
        leaf priority {
          type string;
        }
        leaf retransmit-interval {
          type string;
        }
        leaf transmit-delay {
          type string;
        }
      }
      leaf mtu {
        type string;
      }
    }
    leaf load-interval {
      type string;
    }
    leaf max-reserved-bandwidth {
      type string;
    }
    container mls {
      container qos {
        leaf channel-consistency {
          type string;
          // NCS drop default statement
        }
        leaf trust {
          type string;
        }
        leaf vlan-based {
          type empty;
        }
      }
    }
    leaf mtu {
      type string;
    }
    container power {
      container inline {
        leaf consumption {
          type string;
        }
      }
    }
    container service-policy {
      leaf history {
        type empty;
      }
      leaf input {
        type string;
      }
      leaf output {
        type string;
      }
      container type {
        container performance-monitor {
          leaf direction {
            tailf:cli-drop-node-name;
            type string;
          }
          leaf name {
            tailf:cli-drop-node-name;
            type string;
          }
        }
      }
    }
    leaf shutdown {
      type empty;
    }
    container standby {
      leaf version {
        type string;
      }
      leaf bfd {
        type empty;
      }
      container delay {
        leaf minimum {
          type string;
        }
        leaf reload {
          type string;
        }
      }
      leaf mac-refresh {
        type string;
      }
      container use-bia {
        presence "true";
        container scope {
          leaf interface {
            type empty;
          }
        }
      }
      list standby-list {
        // NCS patched for predictable order
        ordered-by user;
        tailf:cli-drop-node-name;
        tailf:cli-suppress-mode;
        key "group-number";
        leaf group-number {
          type string;
        }
        container authentication {
          choice auth {
            leaf word {
              tailf:cli-drop-node-name;
              type string;
            }
            container md5 {
              leaf key-chain {
                type string;
              }
              container key-string {
                leaf encrypt {
                  tailf:cli-drop-node-name;
                  type string;
                }
                leaf string {
                  tailf:cli-drop-node-name;
                  type string;
                }
                leaf timeout {
                  type string;
                }
              }
            }
            leaf text {
              type string;
            }
          }
        }
        leaf follow {
          type string;
        }
        container ip {
          presence "true";
          leaf address {
            tailf:cli-drop-node-name;
            type string;
          }
          leaf secondary {
            type empty;
          }
        }
        leaf ipv6 {
          type string;
        }
        leaf mac-address {
          type string;
        }
        leaf name {
          type string;
        }
        container preempt {
          presence "true";
          container delay {
            leaf minimum {
              type string;
            }
            leaf reload {
              type string;
            }
            leaf sync {
              type string;
            }
          }
        }
        leaf priority {
          type string;
        }
        container redirect {
          container advertisement {
            container authentication {
              container md5 {
                leaf key-chain {
                  type string;
                }
                container key-string {
                  leaf encrypt {
                    tailf:cli-drop-node-name;
                    type string;
                  }
                  leaf string {
                    tailf:cli-drop-node-name;
                    type string;
                  }
                  leaf timeout {
                    type string;
                  }
                }
              }
            }
          }
          container timers {
            leaf advertisement {
              tailf:cli-drop-node-name;
              type string;
            }
            leaf holddown {
              tailf:cli-drop-node-name;
              type string;
            }
          }
          leaf unknown {
            type empty;
          }
        }
        container timers {
          container hello-interval {
            tailf:cli-drop-node-name;
            choice hello-interval-choice {
              leaf seconds {
                tailf:cli-drop-node-name;
                type string;
              }
              leaf msec {
                type string;
              }
            }
          }
          container hold-time {
            tailf:cli-drop-node-name;
            choice hold-time-choice {
              leaf seconds {
                tailf:cli-drop-node-name;
                type string;
              }
              leaf msec {
                type string;
              }
            }
          }
        }
      }
    }
    container storm-control {
      container action {
        leaf level {
          type string;
        }
      }
      container broadcast {
        leaf level {
          type string;
        }
      }
      container multicast {
        leaf level {
          type string;
        }
      }
      container unicast {
        leaf level {
          type string;
        }
      }
    }
    container wrr-queue {
      container bandwidth {
        choice bandwidth-choice {
          case a {
            leaf weight-1 {
              tailf:cli-drop-node-name;
              type string;
            }
            leaf weight-2 {
              tailf:cli-drop-node-name;
              type string;
            }
            leaf weight-3 {
              tailf:cli-drop-node-name;
              type string;
            }
            leaf weight-4 {
              tailf:cli-drop-node-name;
              type string;
            }
            leaf weight-5 {
              tailf:cli-drop-node-name;
              type string;
            }
            leaf weight-6 {
              tailf:cli-drop-node-name;
              type string;
            }
            leaf weight-7 {
              tailf:cli-drop-node-name;
              type string;
            }
          }
          case b {
            container percent {
              leaf percent-1 {
                tailf:cli-drop-node-name;
                type string;
              }
              leaf percent-2 {
                tailf:cli-drop-node-name;
                type string;
              }
              leaf percent-3 {
                tailf:cli-drop-node-name;
                type string;
              }
              leaf percent-4 {
                tailf:cli-drop-node-name;
                type string;
              }
              leaf percent-5 {
                tailf:cli-drop-node-name;
                type string;
              }
              leaf percent-6 {
                tailf:cli-drop-node-name;
                type string;
              }
              leaf percent-7 {
                tailf:cli-drop-node-name;
                type string;
              }
            }
          }
        }
      }
      list cos-map {
        // NCS patched for predictable order
        ordered-by user;
        tailf:cli-suppress-mode;
        key "queue-id threshold-id";
        leaf queue-id {
          type string;
        }
        leaf threshold-id {
          type string;
        }
        leaf-list cos-values {
          // NCS patched for predictable order
          ordered-by user;
          tailf:cli-drop-node-name;
          // NCS drop max-elements statement
          type string;
        }
      }
      container queue-limit {
        leaf weight-a {
          tailf:cli-drop-node-name;
          type string;
        }
        leaf weight-b {
          tailf:cli-drop-node-name;
          type string;
        }
        leaf weight-c {
          tailf:cli-drop-node-name;
          type string;
        }
      }
      container random-detect {
        list max-threshold {
          // NCS patched for predictable order
          ordered-by user;
          tailf:cli-suppress-mode;
          key "id";
          leaf id {
            type string;
          }
          uses ncs_template_queue-size-grouping;
        }
        list min-threshold {
          // NCS patched for predictable order
          ordered-by user;
          tailf:cli-suppress-mode;
          key "id";
          leaf id {
            type string;
          }
          uses ncs_template_queue-size-grouping;
        }
      }
      list threshold {
        // NCS patched for predictable order
        ordered-by user;
        tailf:cli-suppress-mode;
        key "id";
        leaf id {
          type string;
        }
        uses ncs_template_queue-size-grouping;
      }
    }
    container priority-queue {
      container cos-map {
        leaf id {
          tailf:cli-drop-node-name;
          type string;
        }
        leaf-list cos-values {
          // NCS patched for predictable order
          ordered-by user;
          tailf:cli-drop-node-name;
          // NCS drop max-elements statement
          type string;
        }
      }
      leaf out {
        type empty;
      }
    }
    container rep {
      container block {
        container port {
          choice port-choice {
            leaf neighbor-offset {
              tailf:cli-drop-node-name;
              type string;
            }
            leaf id {
              type string;
            }
            leaf preferred {
              type empty;
            }
          }
          leaf vlan {
            type string;
          }
        }
      }
      container preempt {
        leaf delay {
          type string;
        }
      }
      container segment {
        leaf id {
          tailf:cli-drop-node-name;
          type string;
        }
        leaf edge {
          type empty;
        }
        leaf primary {
          // NCS drop when statement
          type empty;
        }
        leaf preferred {
          type empty;
        }
      }
      container stcn {
        leaf segment {
          type string;
        }
        leaf stp {
          type empty;
        }
      }
    }
    container rcv-queue {
      list cos-map {
        // NCS patched for predictable order
        ordered-by user;
        tailf:cli-suppress-mode;
        key "queue-id threshold-id";
        leaf queue-id {
          type string;
        }
        leaf threshold-id {
          type string;
        }
        leaf-list cos-values {
          // NCS patched for predictable order
          ordered-by user;
          tailf:cli-drop-node-name;
          // NCS drop max-elements statement
          type string;
        }
      }
    }
    container udld {
      container port {
        presence "true";
        choice port-choice {
          leaf aggressive {
            type empty;
          }
          leaf disable {
            type empty;
          }
        }
      }
    }
    container peer {
      container default {
        container ip {
          container address {
            choice address-choice {
              leaf dhcp {
                type empty;
              }
              container dhcp-pool {
                presence "true";
                leaf pools {
                  tailf:cli-drop-node-name;
                  type string;
                }
              }
              container pool {
                presence "true";
                leaf pools {
                  tailf:cli-drop-node-name;
                  type string;
                }
              }
            }
          }
        }
      }
    }
  }

  grouping ncs_template_interface-ethernet-grouping {
    container carrier-delay {
      choice delay-choice {
        leaf seconds {
          tailf:cli-drop-node-name;
          type string;
        }
        leaf msec {
          type string;
        }
      }
    }
    container channel-group {
      leaf number {
        tailf:cli-drop-node-name;
        type string;
      }
      leaf mode {
        type string;
      }
    }
    leaf channel-protocol {
      type string;
    }
    container ethernet {
      container oam {
        presence "true";
        leaf max-rate {
          type string;
        }
        leaf min-rate {
          type string;
        }
        leaf mode {
          type string;
        }
        leaf timeout {
          type string;
        }
      }
    }
    leaf negotiation {
      type string;
    }
    leaf duplex {
      type string;
    }
    leaf speed {
      type string;
    }
    container xconnect {
      leaf address {
        tailf:cli-drop-node-name;
        type string;
      }
      leaf vcid {
        tailf:cli-drop-node-name;
        type string;
      }
      leaf encapsulation {
        type string;
      }
      leaf manual {
        // NCS drop when statement
        type empty;
      }
      leaf sequence {
        // NCS drop when statement
        type string;
      }
      leaf pw-class {
        type string;
      }
    }
    container pppoe {
      container enable {
        presence "true";
        leaf group {
          type string;
        }
      }
      leaf max-sessions {
        type string;
      }
    }
  }

  grouping ncs_template_interface-zone-member-grouping {
    container zone-member {
      leaf security {
        type string;
      }
    }
  }

  grouping ncs_template_interface-pointtopoint-grouping {
    container ppp {
      leaf accounting {
        type string;
      }
      container authentication {
        leaf method {
          tailf:cli-drop-node-name;
          type string;
        }
        leaf list-name {
          tailf:cli-drop-node-name;
          type string;
        }
        leaf chap {
          // NCS drop when statement
          type empty;
        }
        leaf callback {
          type empty;
        }
        leaf callin {
          type empty;
        }
        leaf callout {
          type empty;
        }
        leaf default {
          type empty;
        }
        leaf eap {
          // NCS drop when statement
          type empty;
        }
        leaf ms-chap {
          // NCS drop when statement
          type empty;
        }
        leaf ms-chap-v2 {
          // NCS drop when statement
          type empty;
        }
        leaf one-time {
          type empty;
        }
        leaf optional {
          type empty;
        }
        leaf pap {
          // NCS drop when statement
          type empty;
        }
      }
      leaf authorization {
        type string;
      }
      container ipcp {
        container dns {
          leaf primary {
            tailf:cli-drop-node-name;
            type string;
          }
        }
      }
      container multilink {
        presence "true";
        container links {
          container minimum {
            leaf minimum-value {
              tailf:cli-drop-node-name;
              type string;
            }
            leaf mandatory {
              type empty;
            }
          }
        }
        leaf group {
          type string;
        }
        container fragment {
          container delay {
            leaf delay-value {
              tailf:cli-drop-node-name;
              type string;
            }
            leaf additional-delay-value {
              tailf:cli-drop-node-name;
              type string;
            }
          }
        }
      }
    }
  }

  grouping ncs_template_crypto-pki-token-grouping {
    container removal {
      leaf timeout {
        type string;
      }
    }
  }

  grouping ncs_template_max-path-grouping {
    container max-path {
      tailf:cli-drop-node-name;
      leaf max {
        tailf:cli-drop-node-name;
        type string;
        // NCS drop default statement
      }
      leaf import {
        type string;
      }
    }
  }

  grouping ncs_template_metric-route-map-grouping {
    leaf metric {
      type string;
    }
    leaf route-map {
      type string;
    }
  }

  grouping ncs_template_route-map-metric-grouping {
    leaf route-map {
      type string;
    }
    leaf metric {
      type string;
    }
  }

  grouping ncs_template_redistribute-isis-grouping {
    choice osi-ip-choice {
      leaf ip {
        type empty;
      }
      leaf clns {
        type empty;
      }
    }
    leaf routes {
      tailf:cli-drop-node-name;
      type string;
    }
    uses ncs_template_metric-route-map-grouping;
  }

  grouping ncs_template_bgp-address-family-grouping {
    container aggregate-address {
      leaf address {
        tailf:cli-drop-node-name;
        type string;
      }
      leaf mask {
        tailf:cli-drop-node-name;
        type string;
      }
      leaf advertise-map {
        type string;
      }
      leaf as-set {
        type empty;
      }
      leaf attribute-map {
        type string;
      }
      leaf as-override {
        type empty;
      }
      leaf route-map {
        type string;
      }
      leaf summary-only {
        type empty;
      }
      leaf suppress-map {
        type string;
      }
    }
    container bgp {
      leaf router-id {
        type string;
      }
      leaf always-compare-med {
        type empty;
      }
      container bestpath {
        leaf compare-routerid {
          type empty;
        }
        container cost-community {
          leaf ignore {
            type empty;
          }
        }
        container med {
          choice med-choice {
            container confed {
              presence "Compare MED among confederation paths";
              leaf missing-at-worst {
                type empty;
              }
            }
            leaf missing-at-worst {
              type empty;
            }
          }
        }
      }
      container client-to-client {
        leaf reflection {
          type empty;
        }
      }
      leaf cluster-id {
        type string;
      }
      container confederation {
        leaf identifier {
          type string;
        }
        container peers {
          presence "Peer ASs in BGP confederation";
          leaf-list peers-as {
            // NCS patched for predictable order
            ordered-by user;
            tailf:cli-drop-node-name;
            type string;
          }
        }
      }
      container dampening {
        presence "enable bgp route-flap dampening";
        choice dampening-choice {
          leaf route-map {
            type string;
          }
          container dampen {
            tailf:cli-drop-node-name;
            leaf half-life-time {
              tailf:cli-drop-node-name;
              type string;
            }
            leaf reuse-time {
              tailf:cli-drop-node-name;
              type string;
            }
            leaf suppress-time {
              tailf:cli-drop-node-name;
              type string;
            }
            leaf max-suppress-time {
              tailf:cli-drop-node-name;
              type string;
            }
          }
        }
      }
      container default {
        choice default-choice {
          leaf ipv4-unicast {
            type string;
            // NCS drop default statement
          }
          leaf local-preference {
            type string;
          }
          leaf route-target {
            type string;
          }
        }
      }
      leaf deterministic-med {
        type empty;
      }
      leaf dmzlink-bw {
        type empty;
      }
      leaf enforce-first-as {
        type empty;
      }
      leaf fast-external-fallover {
        type empty;
      }
      container graceful-restart {
        presence "Graceful restart capability parameters";
        leaf restart-time {
          type string;
        }
        leaf stalepath-time {
          type string;
        }
      }
      list inject-map {
        // NCS patched for predictable order
        ordered-by user;
        key "name";
        leaf name {
          type string;
        }
        leaf exist-map {
          type string;
        }
        leaf copy-attributes {
          type empty;
        }
      }
      leaf log-neighbor-changes {
        type empty;
      }
      leaf maxas-limit {
        type string;
      }
      container nexthop {
        container trigger {
          leaf delay {
            type string;
          }
          leaf enable {
            type string;
            // NCS drop default statement
          }
        }
      }
      leaf redistribute-internal {
        type empty;
      }
      container regexp {
        leaf deterministic {
          type empty;
        }
      }
      leaf scan-time {
        type string;
      }
      leaf soft-reconfig-backup {
        type empty;
      }
      leaf suppress-inactive {
        type empty;
      }
      leaf update-delay {
        type string;
      }
    }
    container default-information {
      leaf originate {
        type empty;
      }
    }
    leaf default-metric {
      type string;
    }
    container distance {
      container bgp {
        leaf extern-as {
          tailf:cli-drop-node-name;
          type string;
        }
        leaf internal-as {
          tailf:cli-drop-node-name;
          type string;
        }
        leaf local {
          tailf:cli-drop-node-name;
          type string;
        }
      }
      list adm-distance {
        // NCS patched for predictable order
        ordered-by user;
        tailf:cli-drop-node-name;
        tailf:cli-suppress-mode;
        key "distance srcip wildbits";
        leaf distance {
          type string;
        }
        leaf srcip {
          type string;
        }
        leaf wildbits {
          type string;
        }
        leaf acl {
          tailf:cli-drop-node-name;
          type string;
        }
      }
    }
    list distribute-list {
      // NCS patched for predictable order
      ordered-by user;
      tailf:cli-suppress-mode;
      key "id";
      leaf id {
        type ncs_template_bgp-distribute-list-type;
      }
      choice in-out-choice {
        container in {
          presence "enable incoming routing updates";
          leaf interface {
            type string;
          }
        }
        container out {
          presence "enable outgoing routing updates";
          leaf interface {
            type string;
          }
        }
      }
    }
    container maximum-paths {
      choice max-path-choice {
        case eibgp-case {
          container eibgp {
            uses ncs_template_max-path-grouping;
          }
        }
        case ibgp-case {
          container ibgp {
            choice ibgp-choice {
              case a {
                container unequal-cost {
                  uses ncs_template_max-path-grouping;
                }
              }
              case b {
                uses ncs_template_max-path-grouping;
              }
            }
          }
        }
        case none-case {
          uses ncs_template_max-path-grouping;
        }
        case import-case {
          leaf import {
            type string;
          }
        }
      }
    }
    list neighbor {
      // NCS patched for predictable order
      ordered-by user;
      tailf:cli-suppress-mode;
      // NCS drop must statement
      key "id";
      leaf id {
        type string;
      }
      container peer-group {
        presence "true";
        leaf peer-group-name {
          tailf:cli-drop-node-name;
          type string;
        }
      }
      leaf remote-as {
        type string;
      }
      container local-as {
        presence "Specify a local-as number";
        leaf as-no {
          tailf:cli-drop-node-name;
          type string;
        }
        leaf no-prepend {
          type empty;
        }
        leaf replace-as {
          type empty;
        }
        leaf dual-as {
          type empty;
        }
      }
      leaf activate {
        type empty;
      }
      leaf advertisement-interval {
        type string;
      }
      container allowas-in {
        presence "accept as-paths";
        leaf as-number {
          tailf:cli-drop-node-name;
          type string;
        }
      }
      container as-override {
        presence "true";
        leaf disable {
          type empty;
        }
      }
      container capability {
        container orf {
          leaf-list prefix-list {
            // NCS patched for predictable order
            ordered-by user;
            // NCS drop max-elements statement
            type string;
          }
        }
      }
      container default-originate {
        presence "enable originate default route to this neighbour";
        leaf route-map {
          type string;
        }
      }
      leaf description {
        type string;
      }
      leaf disable-connected-check {
        type empty;
      }
      list distribute-list {
        // NCS patched for predictable order
        ordered-by user;
        tailf:cli-suppress-mode;
        key "inout";
        leaf inout {
          type string;
        }
        leaf accesslist {
          tailf:cli-drop-node-name;
          type ncs_template_bgp-distribute-list-type2;
          // NCS drop mandatory statement
        }
      }
      leaf dmzlink-bw {
        type empty;
      }
      container ebgp-multihop {
        presence "Allow EBGP neighbors not on directly connected networks";
        leaf max-hop {
          tailf:cli-drop-node-name;
          type string;
        }
      }
      leaf fall-over {
        type empty;
      }
      list filter-list {
        // NCS patched for predictable order
        ordered-by user;
        tailf:cli-suppress-mode;
        key "inout";
        leaf inout {
          type string;
        }
        leaf as-path-list {
          tailf:cli-drop-node-name;
          type string;
          // NCS drop mandatory statement
        }
      }
      container inherit {
        leaf peer-policy {
          type string;
        }
        leaf peer-session {
          type string;
        }
      }
      container maximum-prefix {
        leaf max-prefix-no {
          tailf:cli-drop-node-name;
          type string;
        }
        leaf threshold {
          tailf:cli-drop-node-name;
          type string;
        }
        leaf restart {
          type string;
        }
        leaf warning-only {
          type empty;
        }
      }
      leaf next-hop-self {
        type empty;
      }
      leaf next-hop-unchanged {
        type empty;
      }
      container password {
        leaf enctype {
          tailf:cli-drop-node-name;
          type string;
          // NCS drop default statement
        }
        leaf text {
          tailf:cli-drop-node-name;
          type string;
        }
      }
      list prefix-list {
        // NCS patched for predictable order
        ordered-by user;
        tailf:cli-suppress-mode;
        key "inout";
        leaf inout {
          type string;
        }
        leaf prefix-list-name {
          tailf:cli-drop-node-name;
          type string;
          // NCS drop mandatory statement
        }
      }
      leaf remove-private-as {
        type empty;
      }
      list route-map {
        // NCS patched for predictable order
        ordered-by user;
        tailf:cli-suppress-mode;
        key "inout";
        leaf inout {
          type string;
        }
        leaf route-map-name {
          tailf:cli-drop-node-name;
          type string;
          // NCS drop mandatory statement
        }
      }
      leaf route-reflector-client {
        type empty;
      }
      container send-community {
        presence "true";
        leaf send-community-where {
          tailf:cli-drop-node-name;
          type string;
        }
      }
      container send-label {
        leaf send-label-explicit {
          tailf:cli-drop-node-name;
          type string;
        }
      }
      leaf shutdown {
        type empty;
      }
      leaf soft-reconfiguration {
        type string;
      }
      container timers {
        leaf keepalive-interval {
          tailf:cli-drop-node-name;
          type string;
        }
        leaf holdtime {
          tailf:cli-drop-node-name;
          type string;
        }
        leaf minimum-neighbor-hold {
          tailf:cli-drop-node-name;
          type string;
        }
      }
      container translate-update {
        container ipv4 {
          container multicast {
            presence "Address Family modifier";
            leaf unicast {
              type empty;
            }
          }
        }
      }
      container transport {
        leaf connection-mode {
          type string;
        }
      }
      container ttl-security {
        leaf hops {
          type string;
        }
      }
      leaf unsuppress-map {
        type string;
      }
      container update-source {
        // NCS drop tailf-common:cli-diff-dependency statement
        uses ncs_template_interface-grouping;
      }
      leaf version {
        type string;
      }
      leaf weight {
        type string;
      }
      container ha-mode {
        container graceful-restart {
          presence "true";
          leaf disable {
            type empty;
          }
        }
        container sso {
          presence "true";
          leaf disable {
            type empty;
          }
        }
      }
    }
    list network {
      // NCS patched for predictable order
      ordered-by user;
      tailf:cli-suppress-mode;
      key "number";
      leaf number {
        type string;
      }
      leaf backdoor {
        type empty;
      }
      leaf mask {
        type string;
      }
      leaf route-map {
        type string;
      }
    }
    container redistribute {
      container bgp {
        leaf as-no {
          tailf:cli-drop-node-name;
          type string;
        }
        uses ncs_template_metric-route-map-grouping;
      }
      container connected {
        presence "Connected";
        uses ncs_template_metric-route-map-grouping;
      }
      container dvmrp {
        presence "Redistribution of DVMRP into BGP IPv4 Multicast";
        uses ncs_template_route-map-metric-grouping;
      }
      container eigrp {
        leaf as-no {
          tailf:cli-drop-node-name;
          type string;
        }
        uses ncs_template_metric-route-map-grouping;
      }
      container isis {
        list isis-area {
          // NCS patched for predictable order
          ordered-by user;
          tailf:cli-drop-node-name;
          key "name";
          leaf name {
            type string;
          }
          uses ncs_template_redistribute-isis-grouping;
        }
        container default {
          tailf:cli-drop-node-name;
          uses ncs_template_redistribute-isis-grouping;
        }
      }
      container iso-igrp {
        list iso-igrp-area {
          // NCS patched for predictable order
          ordered-by user;
          tailf:cli-drop-node-name;
          key "name";
          leaf name {
            type string;
          }
          uses ncs_template_route-map-metric-grouping;
        }
        container default {
          uses ncs_template_route-map-metric-grouping;
        }
      }
      container mobile {
        presence "Mobile routes";
        uses ncs_template_metric-route-map-grouping;
      }
      container odr {
        presence "On Demand stub Routes";
        uses ncs_template_metric-route-map-grouping;
      }
      list ospf {
        // NCS patched for predictable order
        ordered-by user;
        key "id";
        leaf id {
          type string;
        }
        list vrf {
          // NCS patched for predictable order
          ordered-by user;
          // NCS drop tailf-common:cli-diff-dependency statement
          // NCS drop tailf-common:cli-diff-dependency statement
          key "name";
          leaf name {
            type string;
          }
          container match;
          uses ncs_template_metric-route-map-grouping;
        }
        container non-vrf {
          tailf:cli-drop-node-name;
          container match;
          uses ncs_template_metric-route-map-grouping;
        }
      }
      container rip {
        presence "Routing Information Protocol (RIP)";
        uses ncs_template_metric-route-map-grouping;
      }
      container static {
        presence "Static routes";
        uses ncs_template_metric-route-map-grouping;
      }
    }
    leaf synchronization {
      type empty;
    }
    leaf auto-summary {
      type string;
      // NCS drop default statement
    }
    leaf table-map {
      type string;
    }
    container timers {
      leaf keepalive-interval {
        tailf:cli-drop-node-name;
        type string;
      }
      leaf holdtime {
        tailf:cli-drop-node-name;
        type string;
      }
      leaf minimum-neighbor-hold {
        tailf:cli-drop-node-name;
        type string;
      }
    }
  }

  grouping ncs_template_ospf-ospfv3-common-address-family-grouping {
    container default-information {
      container originate {
        presence "Distribute a default route";
        leaf always {
          type empty;
        }
        leaf metric {
          type string;
        }
        leaf metric-type {
          type ncs_template_ospf-metric-type;
        }
        leaf route-map {
          type string;
        }
      }
    }
    leaf default-metric {
      type string;
    }
    container discard-route {
      presence "Enable or disable discard-route installation";
      leaf external {
        type string;
      }
      leaf internal {
        type string;
      }
    }
    container distance {
      container ospf-distance {
        tailf:cli-drop-node-name;
        leaf distance {
          tailf:cli-drop-node-name;
          type string;
        }
        leaf ip {
          tailf:cli-drop-node-name;
          type string;
        }
        leaf wildcard {
          tailf:cli-drop-node-name;
          type string;
        }
        leaf acl-name {
          tailf:cli-drop-node-name;
          type ncs_template_access-list-standard-id-type;
        }
      }
      container ospf {
        leaf external {
          type string;
        }
        leaf inter-area {
          type string;
        }
        leaf intra-area {
          type string;
        }
      }
    }
    leaf maximum-paths {
      type string;
    }
    container redistribute {
      uses ncs_template_ospf-redistribute-grouping;
      container bgp {
        uses ncs_template_ospf-redistribute-bgp-grouping;
      }
      container connected {
        presence "Connected";
        uses ncs_template_ospf-redistribute-grouping;
      }
      container eigrp {
        uses ncs_template_ospf-redistribute-bgp-grouping;
      }
      container isis {
        presence "ISO IS-IS";
        choice isis-level-routes-isis-area-choice {
          leaf isis-level-routes {
            tailf:cli-drop-node-name;
            type string;
          }
          list isis-area {
            // NCS patched for predictable order
            ordered-by user;
            tailf:cli-suppress-mode;
            tailf:cli-drop-node-name;
            key "name";
            leaf name {
              type string;
            }
            uses ncs_template_ospf-redistribute-grouping;
          }
        }
        uses ncs_template_ospf-redistribute-grouping;
      }
      container iso-igrp {
        presence "IGRP for OSI networks";
        choice area-tag-route-map-choice {
          container area-tag-route-map-container {
            tailf:cli-drop-node-name;
            leaf area-tag {
              tailf:cli-drop-node-name;
              type string;
            }
            leaf route-map {
              type string;
            }
          }
          leaf route-map {
            type string;
          }
        }
        container iso-igrp-container {
          tailf:cli-drop-node-name;
          uses ncs_template_ospf-iso-igrp-redistribute-grouping;
        }
      }
      container maximum-prefix {
        leaf number {
          tailf:cli-drop-node-name;
          type string;
        }
        container threshold-warning-only-container {
          tailf:cli-drop-node-name;
          leaf threshold {
            tailf:cli-drop-node-name;
            type string;
          }
          leaf warning-only {
            type empty;
          }
        }
      }
      container mobile {
        presence "Mobile routes";
        uses ncs_template_ospf-redistribute-grouping;
      }
      container odr {
        presence "On Demand stub Routes";
        uses ncs_template_ospf-redistribute-grouping;
      }
      list ospf {
        // NCS patched for predictable order
        ordered-by user;
        tailf:cli-suppress-mode;
        key "id";
        leaf id {
          type string;
        }
        container match {
          container internal {
            presence "Redistribute OSPF internal routes";
            uses ncs_template_ospf-redistribute-match-grouping;
          }
          container external {
            presence "Redistribute OSPF external routes";
            leaf external-routes {
              tailf:cli-drop-node-name;
              type ncs_template_redist-ospf-external-type;
            }
            uses ncs_template_ospf-redistribute-match-grouping;
          }
          container nssa-external {
            presence "Redistribute OSPF NSSA external routes";
            leaf nssa-external-routes {
              tailf:cli-drop-node-name;
              type ncs_template_redist-ospf-external-type;
            }
            uses ncs_template_ospf-redistribute-match-grouping;
          }
        }
        uses ncs_template_ospf-redistribute-grouping;
        leaf vrf {
          // NCS drop tailf-common:cli-diff-dependency statement
          // NCS drop tailf-common:cli-diff-dependency statement
          type string;
        }
      }
      container rip {
        presence "Routing Information Protocol (RIP)";
        uses ncs_template_ospf-redistribute-grouping;
      }
      container static {
        presence "Static routes";
        uses ncs_template_ospf-redistribute-grouping;
      }
    }
  }

  grouping ncs_template_ospf-ospfv3-common-grouping {
    list area {
      // NCS patched for predictable order
      ordered-by user;
      tailf:cli-suppress-mode;
      key "id";
      leaf id {
        type ncs_template_ospf-area-type;
      }
      container authentication {
        presence "true";
        leaf message-digest {
          type empty;
        }
      }
      leaf default-cost {
        type string;
      }
      list filter-list {
        // NCS patched for predictable order
        ordered-by user;
        tailf:cli-suppress-mode;
        key "in-out";
        leaf prefix {
          // NCS drop mandatory statement
          type string;
        }
        leaf in-out {
          type string;
        }
      }
      container nssa {
        presence "Specify a NSSA area";
        container default-information-originate {
          presence "Originate Type 7 default into NSSA area";
          leaf metric {
            type string;
          }
          leaf metric-type {
            type ncs_template_ospf-metric-type;
          }
        }
        leaf no-ext-capability {
          type empty;
        }
        leaf no-redistribution {
          type empty;
        }
        leaf no-summary {
          type empty;
        }
        container translate {
          container type7 {
            leaf suppress-fa {
              type empty;
            }
          }
        }
      }
      list range {
        // NCS patched for predictable order
        ordered-by user;
        tailf:cli-suppress-mode;
        key "ip mask";
        leaf ip {
          type string;
        }
        leaf mask {
          type string;
        }
        choice advertise-choice {
          leaf advertise {
            type empty;
          }
          leaf not-advertise {
            type empty;
          }
        }
        leaf cost {
          type string;
        }
      }
      list sham-link {
        // NCS patched for predictable order
        ordered-by user;
        tailf:cli-suppress-mode;
        key "source dest";
        leaf source {
          type string;
        }
        leaf dest {
          type string;
        }
        leaf cost {
          type string;
        }
      }
      container stub {
        presence "Specify a stub area";
        leaf no-ext-capability {
          type empty;
        }
        leaf no-summary {
          type empty;
        }
      }
      list virtual-link {
        // NCS patched for predictable order
        ordered-by user;
        tailf:cli-suppress-mode;
        key "id";
        leaf id {
          type string;
        }
        leaf authentication {
          type empty;
        }
        container authentication-key {
          leaf auth-type {
            tailf:cli-drop-node-name;
            type string;
          }
          leaf auth-key {
            tailf:cli-drop-node-name;
            type string;
          }
        }
        leaf dead-interval {
          type string;
        }
        leaf hello-interval {
          type string;
        }
        list message-digest-key {
          // NCS patched for predictable order
          ordered-by user;
          tailf:cli-suppress-mode;
          key "id";
          leaf id {
            type string;
          }
          container md5 {
            leaf auth-type {
              tailf:cli-drop-node-name;
              type string;
            }
            leaf auth-key {
              tailf:cli-drop-node-name;
              type string;
            }
          }
        }
        leaf retransmit-interval {
          type string;
        }
        leaf transmit-delay {
          type string;
        }
      }
    }
    container auto-cost {
      presence "Calculate OSPF interface cost according to bandwidth";
      leaf reference-bandwidth {
        type string;
      }
    }
    container bfd {
      leaf all-interfaces {
        type empty;
      }
    }
    container interface-id {
      leaf snmp-if-index {
        type empty;
      }
    }
    container log-adjacency-changes {
      presence "true";
      leaf detail {
        type empty;
      }
    }
    container max-lsa {
      leaf number {
        tailf:cli-drop-node-name;
        type string;
      }
      container options {
        tailf:cli-drop-node-name;
        leaf threshold-value {
          tailf:cli-drop-node-name;
          type string;
        }
        leaf ignore-count {
          type string;
        }
        leaf ignore-time {
          type string;
        }
        leaf reset-time {
          type string;
        }
        leaf warning-only {
          type empty;
        }
      }
    }
    uses ncs_template_passive-interface-grouping;
    container queue-depth {
      container hello {
        uses ncs_template_queue-depth-grouping;
      }
      container update {
        uses ncs_template_queue-depth-grouping;
      }
    }
    container timers {
      container lsa {
        leaf arrival {
          type string;
        }
      }
      container pacing {
        leaf flood {
          type string;
        }
        leaf lsa-group {
          type string;
        }
        leaf retransmission {
          type string;
        }
      }
      container throttle {
        container lsa {
          container all {
            leaf delay {
              tailf:cli-drop-node-name;
              type string;
            }
            leaf min-delay {
              tailf:cli-drop-node-name;
              type string;
            }
            leaf max-delay {
              tailf:cli-drop-node-name;
              type string;
            }
          }
        }
        container spf {
          leaf delay {
            tailf:cli-drop-node-name;
            type string;
          }
          leaf min-delay {
            tailf:cli-drop-node-name;
            type string;
          }
          leaf max-delay {
            tailf:cli-drop-node-name;
            type string;
          }
        }
      }
    }
    leaf router-id {
      type string;
    }
  }

  grouping ncs_template_ospfv3-address-family-grouping;

  grouping ncs_template_queue-depth-grouping {
    leaf options {
      tailf:cli-drop-node-name;
      type string;
      // NCS drop default statement
    }
  }

  grouping ncs_template_ospf-redistribute-match-grouping {
    leaf metric {
      type string;
    }
    leaf subnets {
      type empty;
    }
    leaf route-map {
      type string;
    }
    leaf tag {
      type string;
    }
  }

  grouping ncs_template_ospf-iso-igrp-redistribute-grouping {
    leaf metric {
      type string;
    }
    leaf metric-type {
      type string;
    }
    leaf tag {
      type string;
    }
    leaf subnets {
      type empty;
    }
  }

  grouping ncs_template_ospf-redistribute-grouping {
    container redist-options {
      tailf:cli-drop-node-name;
      uses ncs_template_ospf-iso-igrp-redistribute-grouping;
      leaf route-map {
        type string;
      }
    }
  }

  grouping ncs_template_ospf-redistribute-bgp-grouping {
    leaf as-number {
      tailf:cli-drop-node-name;
      type string;
    }
    uses ncs_template_ospf-redistribute-grouping;
  }

  grouping ncs_template_router-rip-grouping {
    uses ncs_template_address-family-vrf-grouping;
    leaf flash-update-threshold {
      type string;
    }
    leaf input-queue {
      type string;
    }
    leaf output-delay {
      type string;
    }
    uses ncs_template_passive-interface-grouping;
    container traffic-share {
      container min {
        leaf across-interfaces {
          type empty;
        }
      }
    }
  }

  grouping ncs_template_default-redistribute-grouping {
    container connected {
      presence "Connected";
      uses ncs_template_rip-metric-route-map-grouping;
    }
    list bgp {
      // NCS patched for predictable order
      ordered-by user;
      tailf:cli-suppress-mode;
      key "as-number";
      leaf as-number {
        type string;
      }
      uses ncs_template_rip-metric-route-map-grouping;
    }
    list eigrp {
      // NCS patched for predictable order
      ordered-by user;
      tailf:cli-suppress-mode;
      key "as-number";
      leaf as-number {
        type string;
      }
      uses ncs_template_rip-metric-route-map-grouping;
    }
    container isis {
      presence "ISO IS-IS";
      list isis-area {
        // NCS patched for predictable order
        ordered-by user;
        tailf:cli-suppress-mode;
        tailf:cli-drop-node-name;
        key "name";
        leaf name {
          type string;
        }
        uses ncs_template_redist-isis-grouping;
      }
      uses ncs_template_redist-isis-grouping;
    }
    container iso-igrp {
      presence "IGRP for OSI networks";
      list isoigrp-list {
        // NCS patched for predictable order
        ordered-by user;
        tailf:cli-suppress-mode;
        tailf:cli-drop-node-name;
        key "iso-area-tag";
        leaf iso-area-tag {
          type string;
        }
        uses ncs_template_rip-iso-igrp-metric-route-map-grouping;
      }
      uses ncs_template_rip-iso-igrp-metric-route-map-grouping;
    }
    container mobile {
      presence "Mobile routes";
      uses ncs_template_rip-metric-route-map-grouping;
    }
    container odr {
      presence "On Demand stub Routes";
      uses ncs_template_rip-metric-route-map-grouping;
    }
    list ospf {
      // NCS patched for predictable order
      ordered-by user;
      tailf:cli-suppress-mode;
      key "process-id";
      leaf process-id {
        type string;
      }
      list vrf {
        // NCS patched for predictable order
        ordered-by user;
        // NCS drop tailf-common:cli-diff-dependency statement
        // NCS drop tailf-common:cli-diff-dependency statement
        key "name";
        leaf name {
          type string;
        }
      }
      container match {
        container internal {
          presence "Redistribute OSPF internal routes";
          uses ncs_template_rip-metric-route-map-grouping;
        }
        container external {
          presence "Redistribute OSPF external routes";
          leaf external-routes {
            tailf:cli-drop-node-name;
            type ncs_template_redist-ospf-external-type;
          }
          uses ncs_template_rip-metric-route-map-grouping;
        }
        container nssa-external {
          presence "Redistribute OSPF NSSA external routes";
          leaf nssa-external-routes {
            tailf:cli-drop-node-name;
            type ncs_template_redist-ospf-external-type;
          }
          uses ncs_template_rip-metric-route-map-grouping;
        }
      }
      uses ncs_template_rip-metric-route-map-grouping;
    }
    container static {
      presence "Static routes";
      uses ncs_template_rip-metric-route-map-grouping;
    }
    container rip {
      presence "Routing Information Protocol (RIP)";
      uses ncs_template_rip-metric-route-map-grouping;
    }
  }

  grouping ncs_template_distance-grouping {
    container distance {
      leaf distance-leaf {
        tailf:cli-drop-node-name;
        type string;
      }
      list distance-list {
        // NCS patched for predictable order
        ordered-by user;
        tailf:cli-suppress-mode;
        tailf:cli-drop-node-name;
        key "number ip mask";
        leaf number {
          type string;
        }
        leaf ip {
          type string;
        }
        leaf mask {
          type string;
        }
      }
    }
  }

  grouping ncs_template_offset-list-grouping {
    list offset-list {
      // NCS patched for predictable order
      ordered-by user;
      tailf:cli-suppress-mode;
      key "in-out";
      leaf in-out {
        type ncs_template_offset-list-in-out-type;
      }
      leaf offset {
        tailf:cli-drop-node-name;
        // NCS drop mandatory statement
        type string;
      }
    }
  }

  grouping ncs_template_default-router-rip-grouping {
    leaf auto-summary {
      type empty;
    }
    leaf maximum-paths {
      type string;
    }
    list neighbor {
      // NCS patched for predictable order
      ordered-by user;
      tailf:cli-suppress-mode;
      key "ip";
      leaf ip {
        type string;
      }
    }
    list network {
      // NCS patched for predictable order
      ordered-by user;
      tailf:cli-suppress-mode;
      key "ip";
      leaf ip {
        type string;
      }
    }
    leaf validate-update-source {
      type string;
      // NCS drop default statement
    }
  }

  grouping ncs_template_address-family-vrf-grouping {
    uses ncs_template_default-router-rip-grouping;
    container default-information {
      container originate {
        presence "Distribute a default route";
        leaf route-map {
          type string;
        }
      }
    }
    leaf default-metric {
      type string;
    }
    uses ncs_template_distance-grouping;
    uses ncs_template_distribute-list-grouping;
    uses ncs_template_offset-list-grouping;
    container redistribute {
      uses ncs_template_rip-metric-route-map-grouping;
      uses ncs_template_default-redistribute-grouping;
    }
    container timers {
      container basic {
        leaf updates {
          tailf:cli-drop-node-name;
          type string;
        }
        leaf invalid {
          tailf:cli-drop-node-name;
          type string;
        }
        leaf holddown {
          tailf:cli-drop-node-name;
          type string;
        }
        leaf flush {
          tailf:cli-drop-node-name;
          type string;
        }
        leaf sleep {
          tailf:cli-drop-node-name;
          type string;
        }
      }
    }
    leaf version {
      type string;
    }
  }

  grouping ncs_template_redist-isis-grouping {
    container rip-isis-redist {
      tailf:cli-drop-node-name;
      leaf isis-level-routes {
        tailf:cli-drop-node-name;
        type string;
      }
      uses ncs_template_rip-metric-route-map-grouping;
    }
  }

  grouping ncs_template_rip-metric-route-map-grouping {
    container rip-metric-route-map {
      tailf:cli-drop-node-name;
      container metric {
        choice metric-transparent-choice {
          leaf metric-value {
            tailf:cli-drop-node-name;
            type string;
          }
          leaf transparent {
            type empty;
          }
        }
      }
      leaf route-map {
        type string;
      }
    }
  }

  grouping ncs_template_rip-iso-igrp-metric-route-map-grouping {
    container rip-metric-route-map {
      tailf:cli-drop-node-name;
      leaf route-map {
        type string;
      }
      container metric {
        choice metric-transparent-choice {
          leaf metric-value {
            tailf:cli-drop-node-name;
            type string;
          }
          leaf transparent {
            type empty;
          }
        }
      }
    }
  }

  grouping ncs_template_narrow-wide-transition-grouping {
    leaf narrow-wide {
      tailf:cli-drop-node-name;
      type ncs_template_isis-level-type;
    }
    leaf transition {
      type ncs_template_isis-level-type;
    }
  }

  grouping ncs_template_spf-intervals-grouping {
    leaf interval {
      tailf:cli-drop-node-name;
      type string;
    }
    leaf initial-wait {
      tailf:cli-drop-node-name;
      type string;
    }
    leaf minimum-wait {
      tailf:cli-drop-node-name;
      type string;
    }
  }

  grouping ncs_template_authenticate-snp-grouping {
    leaf authenticate {
      type empty;
    }
    leaf snp {
      type string;
    }
  }

  grouping ncs_template_lsp-gen-interval-grouping {
    leaf interval {
      tailf:cli-drop-node-name;
      type string;
    }
    leaf initial-wait {
      tailf:cli-drop-node-name;
      type string;
    }
    leaf wait {
      tailf:cli-drop-node-name;
      type string;
    }
  }

  grouping ncs_template_set-overload-bit-suppress-grouping {
    leaf external {
      type empty;
    }
    leaf interlevel {
      type empty;
    }
  }

  grouping ncs_template_summary-address-metric-tag-grouping {
    leaf metric {
      type string;
    }
    leaf tag {
      type string;
    }
  }

  grouping ncs_template_authentication-level-grouping {
    leaf levels {
      tailf:cli-drop-node-name;
      type ncs_template_authentication-level-type;
    }
  }

  grouping ncs_template_redist-level-grouping {
    leaf levels {
      tailf:cli-drop-node-name;
      type ncs_template_isis-routes-level-type;
    }
  }

  grouping ncs_template_isis-redist-container-content-grouping {
    uses ncs_template_redist-level-grouping;
    leaf metric {
      type string;
    }
    leaf metric-type {
      type string;
    }
    leaf route-map {
      type string;
    }
  }

  grouping ncs_template_isis-redist-grouping {
    container isis-redist-container {
      tailf:cli-drop-node-name;
      uses ncs_template_isis-redist-container-content-grouping;
    }
  }

  grouping ncs_template_isis-redist-af-grouping {
    container isis-redist-af-container {
      tailf:cli-drop-node-name;
      leaf include-connected {
        type empty;
      }
      uses ncs_template_isis-redist-container-content-grouping;
    }
  }

  grouping ncs_template_isis-redist-ospf-match-grouping {
    uses ncs_template_redist-level-grouping;
    leaf metric {
      type string;
    }
    leaf route-map {
      type string;
    }
  }

  grouping ncs_template_isis-redist-clns-ip-grouping {
    uses ncs_template_isis-redist-grouping;
    container clns {
      presence "Redistribution of BGP NSAP routes";
      leaf route-map {
        type string;
      }
    }
    leaf ip {
      type empty;
    }
  }

  grouping ncs_template_isis-address-family-grouping {
    leaf adjacency-check {
      type empty;
    }
    container default-information {
      container originate {
        presence "Distribute a default route";
        leaf route-map {
          type string;
        }
      }
    }
    leaf maximum-paths {
      type string;
    }
    container metric {
      leaf default {
        tailf:cli-drop-node-name;
        type string;
      }
      leaf level-1-2 {
        tailf:cli-drop-node-name;
        type string;
      }
    }
    container prc-interval {
      leaf interval {
        tailf:cli-drop-node-name;
        type string;
      }
      leaf initial-wait {
        tailf:cli-drop-node-name;
        type string;
      }
      leaf minimum-wait {
        tailf:cli-drop-node-name;
        type string;
      }
    }
    container set-overload-bit {
      choice set-overload-bit-choice {
        container on-startup {
          choice on-startup-choice {
            container time {
              tailf:cli-drop-node-name;
              leaf time {
                tailf:cli-drop-node-name;
                type string;
              }
              leaf suppress {
                type empty;
              }
              uses ncs_template_set-overload-bit-suppress-grouping;
            }
            container wait-for-bgp {
              presence "Let BGP decide when to unset the overload bitW";
              container suppress {
                uses ncs_template_set-overload-bit-suppress-grouping;
              }
            }
          }
        }
        container suppress {
          uses ncs_template_set-overload-bit-suppress-grouping;
        }
      }
    }
    container spf-interval {
      choice spf-interval-choice {
        list level-1-2 {
          // NCS patched for predictable order
          ordered-by user;
          tailf:cli-drop-node-name;
          tailf:cli-suppress-mode;
          key "level";
          leaf level {
            type string;
          }
          uses ncs_template_spf-intervals-grouping;
        }
        container intervals {
          tailf:cli-drop-node-name;
          uses ncs_template_spf-intervals-grouping;
        }
      }
    }
    container traffic-share {
      container min {
        leaf across-interface {
          type empty;
        }
      }
    }
  }

  grouping ncs_template_isis-main-grouping {
    container isis-main-container {
      tailf:cli-drop-node-name;
      uses ncs_template_isis-address-family-grouping;
      container address-family {
        container ipv6 {
          container unicast {
            uses ncs_template_isis-address-family-grouping;
            leaf distance {
              type string;
            }
            container multi-topology {
              presence "Enable multi-topology mode";
              leaf transition {
                type empty;
              }
            }
            container redistribute {
              container bgp {
                leaf as-number {
                  tailf:cli-drop-node-name;
                  type string;
                }
                uses ncs_template_isis-redist-af-grouping;
              }
              container connected {
                presence "Connected";
                uses ncs_template_isis-redist-grouping;
              }
              list eigrp {
                // NCS patched for predictable order
                ordered-by user;
                tailf:cli-suppress-mode;
                key "as-number";
                leaf as-number {
                  tailf:cli-drop-node-name;
                  type string;
                }
                uses ncs_template_isis-redist-af-grouping;
              }
              container isis {
                leaf area-tag {
                  tailf:cli-drop-node-name;
                  type string;
                }
                container levels {
                  tailf:cli-drop-node-name;
                  leaf isis-redist-levels1 {
                    tailf:cli-drop-node-name;
                    type string;
                  }
                  leaf into {
                    type empty;
                  }
                  leaf isis-redist-levels2 {
                    tailf:cli-drop-node-name;
                    type string;
                  }
                  leaf distribute-list {
                    type string;
                  }
                }
              }
              container nemo {
                uses ncs_template_isis-redist-af-grouping;
              }
              list ospf {
                // NCS patched for predictable order
                ordered-by user;
                tailf:cli-suppress-mode;
                key "process-id";
                leaf process-id {
                  type string;
                }
                uses ncs_template_isis-redist-af-grouping;
                container match {
                  container internal {
                    presence "Redistribute OSPF internal routes";
                    uses ncs_template_isis-redist-ospf-match-grouping;
                  }
                  container external {
                    presence "Redistribute OSPF external routes";
                    leaf external-routes {
                      tailf:cli-drop-node-name;
                      type ncs_template_redist-ospf-external-type;
                    }
                    uses ncs_template_isis-redist-ospf-match-grouping;
                  }
                  container nssa-external {
                    presence "Redistribute OSPF NSSA external routes";
                    leaf nssa-external-routes {
                      tailf:cli-drop-node-name;
                      type ncs_template_redist-ospf-external-type;
                    }
                    uses ncs_template_isis-redist-ospf-match-grouping;
                  }
                }
              }
              list rip {
                // NCS patched for predictable order
                ordered-by user;
                tailf:cli-suppress-mode;
                key "process";
                leaf process {
                  type string;
                }
                uses ncs_template_isis-redist-af-grouping;
              }
              container static {
                presence "Static routes";
                uses ncs_template_isis-redist-grouping;
              }
            }
            list summary-prefix {
              // NCS patched for predictable order
              ordered-by user;
              tailf:cli-suppress-mode;
              key "prefix";
              leaf prefix {
                type string;
              }
              leaf levels {
                tailf:cli-drop-node-name;
                type string;
              }
            }
          }
        }
      }
      container advertise {
        leaf passive-only {
          type empty;
        }
      }
      container area-password {
        leaf name {
          tailf:cli-drop-node-name;
          type string;
        }
        uses ncs_template_authenticate-snp-grouping;
      }
      container authentication {
        container mode {
          container md5 {
            presence "Keyed message digest";
            uses ncs_template_authentication-level-grouping;
          }
          container text {
            presence "Clear text password";
            uses ncs_template_authentication-level-grouping;
          }
        }
        container key-chain {
          leaf name {
            tailf:cli-drop-node-name;
            type string;
          }
          uses ncs_template_authentication-level-grouping;
        }
        container send-only {
          presence "Authentication send only, receive ignore";
          uses ncs_template_authentication-level-grouping;
        }
      }
      container bfd {
        leaf all-interfaces {
          type empty;
        }
      }
      container distance {
        container clns-container {
          tailf:cli-drop-node-name;
          leaf distance {
            tailf:cli-drop-node-name;
            type string;
          }
          leaf clns {
            type empty;
          }
        }
        container ip-container {
          tailf:cli-drop-node-name;
          leaf distance {
            tailf:cli-drop-node-name;
            type string;
          }
          leaf ip {
            type empty;
          }
        }
        container acl-container {
          tailf:cli-drop-node-name;
          leaf distance {
            tailf:cli-drop-node-name;
            type string;
          }
          list acl {
            // NCS patched for predictable order
            ordered-by user;
            tailf:cli-drop-node-name;
            tailf:cli-suppress-mode;
            key "ip wildcard";
            leaf ip {
              type string;
            }
            leaf wildcard {
              type string;
            }
            leaf acl-name {
              tailf:cli-drop-node-name;
              type ncs_template_access-list-standard-id-type;
            }
          }
        }
      }
      container domain-password {
        leaf name {
          tailf:cli-drop-node-name;
          type string;
        }
        uses ncs_template_authenticate-snp-grouping;
      }
      container fast-flood {
        presence "Flood LSPs (that triggered SPF) before running SPF";
        leaf number {
          tailf:cli-drop-node-name;
          type string;
        }
      }
      container hello {
        container padding {
          presence "Pad hello PDU";
          leaf pad-type {
            tailf:cli-drop-node-name;
            type string;
          }
        }
      }
      container hostname {
        leaf dynamic {
          type empty;
        }
      }
      leaf ignore-lsp-errors {
        type empty;
      }
      container ip {
        container route {
          container priority {
            container high {
              leaf tag {
                type string;
              }
            }
          }
        }
      }
      leaf is-type {
        type string;
      }
      container ispf {
        leaf level {
          tailf:cli-drop-node-name;
          type string;
        }
        leaf number {
          tailf:cli-drop-node-name;
          type string;
        }
      }
      container log-adjacency-changes {
        presence "Log changes in adjacency state";
        leaf all {
          type empty;
        }
      }
      container lsp-full {
        container suppress {
          choice lsp-full-choince {
            container external-interlevel-container {
              tailf:cli-drop-node-name;
              leaf external {
                type empty;
              }
              leaf interlevel {
                type empty;
              }
            }
            leaf none {
              type empty;
            }
          }
        }
      }
      container lsp-gen-interval {
        choice lsp-gen-interval-choice {
          container intervals {
            tailf:cli-drop-node-name;
            uses ncs_template_lsp-gen-interval-grouping;
          }
          container intervals-levels {
            tailf:cli-drop-node-name;
            container intervals-level-1 {
              tailf:cli-drop-node-name;
              leaf level-1 {
                type empty;
              }
              uses ncs_template_lsp-gen-interval-grouping;
            }
            container intervals-level-2 {
              tailf:cli-drop-node-name;
              leaf level-2 {
                type empty;
              }
              uses ncs_template_lsp-gen-interval-grouping;
            }
          }
        }
      }
      leaf lsp-mtu {
        type string;
      }
      leaf lsp-refresh-interval {
        type string;
      }
      leaf max-area-addresses {
        type string;
      }
      leaf max-lsp-lifetime {
        type string;
      }
      container metric-style {
        choice metric-style-choice {
          container narrow {
            presence "true";
            uses ncs_template_narrow-wide-transition-grouping;
          }
          container transition {
            presence "true";
            leaf transition {
              type ncs_template_isis-level-type;
              tailf:cli-drop-node-name;
            }
          }
          container wide {
            presence "true";
            uses ncs_template_narrow-wide-transition-grouping;
          }
        }
      }
      container mpls {
        container traffic-eng {
          leaf level-1 {
            type empty;
          }
          leaf level-2 {
            type empty;
          }
          leaf multicast-intact {
            type empty;
          }
          container router-id {
            // NCS drop tailf-common:cli-diff-dependency statement
            uses ncs_template_interface-grouping;
          }
          container scanner {
            presence "Timer parameters for TE database";
            leaf interval {
              type string;
            }
            leaf max-flash {
              type string;
            }
          }
        }
      }
      list net {
        // NCS patched for predictable order
        ordered-by user;
        tailf:cli-suppress-mode;
        key "tag";
        leaf tag {
          type ncs_template_isis-net;
        }
      }
      container partition {
        leaf avoidance {
          type empty;
        }
      }
      uses ncs_template_passive-interface-grouping;
      container protocol {
        leaf shutdown {
          type empty;
        }
      }
      container redistribute {
        uses ncs_template_isis-redist-grouping;
        container bgp {
          leaf as-number {
            tailf:cli-drop-node-name;
            type string;
          }
          uses ncs_template_isis-redist-clns-ip-grouping;
        }
        container connected {
          presence "Connected";
          uses ncs_template_isis-redist-grouping;
        }
        list eigrp {
          // NCS patched for predictable order
          ordered-by user;
          tailf:cli-suppress-mode;
          key "as-number";
          leaf as-number {
            tailf:cli-drop-node-name;
            type string;
          }
          uses ncs_template_isis-redist-grouping;
        }
        container isis {
          leaf area-tag {
            tailf:cli-drop-node-name;
            type string;
          }
          container ip {
            leaf isis-redist-levels1 {
              tailf:cli-drop-node-name;
              type string;
            }
            leaf into {
              type empty;
            }
            leaf isis-redist-levels2 {
              tailf:cli-drop-node-name;
              type string;
            }
            choice isis-redist-isis-ip-choice {
              leaf distribute-list {
                type string;
              }
              leaf route-map {
                type string;
              }
            }
          }
        }
        container iso-igrp {
          presence "IGRP for OSI networks";
          choice iso-igrp-choice {
            container area-tag-route-map-container {
              tailf:cli-drop-node-name;
              leaf area-tag {
                tailf:cli-drop-node-name;
                type string;
              }
              leaf route-map {
                type string;
              }
            }
            leaf route-map {
              type string;
            }
          }
          uses ncs_template_redist-level-grouping;
          leaf metric {
            type string;
          }
          leaf metric-type {
            type string;
          }
        }
        container maximum-prefix {
          leaf number {
            tailf:cli-drop-node-name;
            type string;
          }
          leaf threshold-value {
            tailf:cli-drop-node-name;
            type string;
          }
          leaf warning-only {
            type empty;
          }
          leaf withdraw {
            type empty;
          }
        }
        container mobile {
          presence "Mobile routes";
          uses ncs_template_isis-redist-grouping;
        }
        container odr {
          presence "On Demand stub Routes";
          uses ncs_template_isis-redist-grouping;
        }
        list ospf {
          // NCS patched for predictable order
          ordered-by user;
          tailf:cli-suppress-mode;
          key "process-id";
          leaf process-id {
            type string;
          }
          uses ncs_template_isis-redist-grouping;
          container match {
            container internal {
              presence "Redistribute OSPF internal routes";
              uses ncs_template_isis-redist-ospf-match-grouping;
            }
            container external {
              presence "Redistribute OSPF external routes";
              leaf external-routes {
                tailf:cli-drop-node-name;
                type ncs_template_redist-ospf-external-type;
              }
              uses ncs_template_isis-redist-ospf-match-grouping;
            }
            container nssa-external {
              presence "Redistribute OSPF NSSA external routes";
              leaf nssa-external-routes {
                tailf:cli-drop-node-name;
                type ncs_template_redist-ospf-external-type;
              }
              uses ncs_template_isis-redist-ospf-match-grouping;
            }
          }
          leaf vrf {
            // NCS drop tailf-common:cli-diff-dependency statement
            // NCS drop tailf-common:cli-diff-dependency statement
            type string;
          }
        }
        container rip {
          presence "Routing Information Protocol (RIP)";
          uses ncs_template_isis-redist-grouping;
        }
        container static {
          presence "Static routes";
          uses ncs_template_isis-redist-clns-ip-grouping;
        }
      }
      container set-attached-bit {
        leaf route-map {
          type string;
        }
      }
      list summary-address {
        // NCS patched for predictable order
        ordered-by user;
        tailf:cli-suppress-mode;
        key "ip mask";
        leaf ip {
          type string;
        }
        leaf mask {
          type string;
        }
        container level-1 {
          presence "Summarize into level-1 area";
          uses ncs_template_summary-address-metric-tag-grouping;
        }
        container level-1-2 {
          presence "Summarize into both area and sub-domain";
          uses ncs_template_summary-address-metric-tag-grouping;
        }
        container level-2 {
          presence "Summarize into level-2 sub-domain";
          uses ncs_template_summary-address-metric-tag-grouping;
        }
        container metric-tag-container {
          tailf:cli-drop-node-name;
          uses ncs_template_summary-address-metric-tag-grouping;
        }
      }
      leaf update-queue-depth {
        type string;
      }
      container use {
        leaf external-metrics {
          type empty;
        }
      }
    }
  }

  grouping ncs_template_interface-switch-grouping {
    container switchport-conf {
      tailf:cli-drop-node-name;
      leaf switchport {
        type string;
      }
    }
    container switchport {
      container access {
        leaf vlan {
          // NCS drop tailf-common:cli-diff-dependency statement
          type string;
        }
      }
      container block {
        leaf multicast {
          type empty;
        }
        leaf unicast {
          type empty;
        }
      }
      container mode {
        choice mode-choice {
          container access {
            presence "true";
          }
          container dot1q-tunnel {
            presence "true";
          }
          leaf dynamic {
            type string;
          }
          container trunk {
            presence "true";
          }
        }
      }
      leaf nonegotiate {
        type empty;
      }
      container port-security {
        presence "true";
        container aging {
          leaf time {
            type string;
          }
          leaf type {
            type string;
          }
        }
        container mac-address {
          leaf sticky {
            type empty;
          }
          leaf hw-address {
            tailf:cli-drop-node-name;
            type string;
          }
          leaf vlan {
            type string;
          }
        }
        container maximum {
          leaf max-addresses {
            tailf:cli-drop-node-name;
            type string;
          }
          leaf vlan {
            type string;
          }
        }
        leaf violation {
          type string;
        }
      }
      container trunk {
        container allowed {
          container vlan {
            choice vlan-choice {
              leaf-list vlans {
                // NCS patched for predictable order
                ordered-by user;
                tailf:cli-range-list-syntax;
                tailf:cli-drop-node-name;
                type string;
              }
              leaf all {
                type empty;
              }
              leaf-list except {
                // NCS patched for predictable order
                ordered-by user;
                tailf:cli-range-list-syntax;
                type string;
              }
              leaf none {
                type empty;
              }
            }
          }
        }
        leaf encapsulation {
          type string;
        }
        container native {
          leaf vlan {
            type string;
          }
        }
        container pruning {
          container vlan {
            choice vlan-choice {
              leaf-list vlans {
                // NCS patched for predictable order
                ordered-by user;
                tailf:cli-range-list-syntax;
                tailf:cli-drop-node-name;
                type string;
              }
              leaf-list except {
                // NCS patched for predictable order
                ordered-by user;
                tailf:cli-range-list-syntax;
                type string;
              }
              leaf none {
                type empty;
              }
            }
          }
        }
      }
      container voice {
        leaf vlan {
          type string;
        }
        container detect {
          container cisco-phone {
            presence "true";
            leaf full-duplex {
              type empty;
            }
          }
        }
      }
      container priority {
        container extend {
          choice trust-choice {
            leaf trust {
              type empty;
            }
            leaf cos {
              type string;
            }
          }
        }
      }
      container autostate {
        leaf exclude {
          type empty;
        }
      }
      leaf protected {
        type empty;
      }
      leaf host {
        type empty;
      }
    }
    container spanning-tree {
      leaf bpdufilter {
        type string;
      }
      container bpduguard {
        choice bpduguard-choice {
          leaf disable {
            type empty;
          }
          leaf enable {
            type empty;
          }
        }
      }
      leaf cost {
        type string;
      }
      leaf guard {
        type string;
      }
      leaf link-type {
        type string;
      }
      container portfast {
        presence "true";
        leaf enable {
          tailf:cli-drop-node-name;
          type string;
        }
        leaf trunk {
          type empty;
        }
      }
      container loopguard {
        leaf default {
          type empty;
        }
      }
    }
    container srr-queue {
      container bandwidth {
        container shape {
          leaf weight1 {
            tailf:cli-drop-node-name;
            type string;
          }
          leaf weight2 {
            tailf:cli-drop-node-name;
            type string;
          }
          leaf weight3 {
            tailf:cli-drop-node-name;
            type string;
          }
          leaf weight4 {
            tailf:cli-drop-node-name;
            type string;
          }
        }
        container share {
          leaf weight1 {
            tailf:cli-drop-node-name;
            type string;
          }
          leaf weight2 {
            tailf:cli-drop-node-name;
            type string;
          }
          leaf weight3 {
            tailf:cli-drop-node-name;
            type string;
          }
          leaf weight4 {
            tailf:cli-drop-node-name;
            type string;
          }
        }
      }
    }
  }

  grouping ncs_template_password-07-grouping {
    leaf level {
      type string;
    }
    leaf type {
      tailf:cli-drop-node-name;
      type string;
    }
    leaf secret {
      tailf:cli-drop-node-name;
      type string;
    }
  }

  grouping ncs_template_aaa-authentication-dot1x-grouping {
    leaf group {
      type string;
    }
  }

  grouping ncs_rpc_notif_vrf-route-target-grouping {
    list export {
      tailf:info
        "Export Target-VPN community";
      tailf:cli-suppress-mode;
      tailf:cli-delete-when-empty;
      key "asn-ip";
      leaf asn-ip {
        type ncs_rpc_notif_asn-ip-type;
      }
    }
    list import {
      tailf:info
        "Import Target-VPN community";
      tailf:cli-suppress-mode;
      tailf:cli-delete-when-empty;
      key "asn-ip";
      leaf asn-ip {
        type ncs_rpc_notif_asn-ip-type;
      }
    }
  }

  grouping ncs_rpc_notif_police-action-transmit-grouping {
    leaf transmit {
      tailf:info
        "transmit packet";
      type empty;
    }
  }

  grouping ncs_rpc_notif_police-action-drop-grouping {
    leaf drop {
      tailf:info
        "drop packet";
      type empty;
    }
  }

  grouping ncs_rpc_notif_police-conform-action-grouping {
    container conform-set-clp-transmit {
      tailf:cli-no-keyword;
      tailf:cli-drop-node-name;
      tailf:cli-flatten-container;
      container conform-action {
        tailf:info
          "action when rate is less than conform burst";
        tailf:cli-flatten-container;
        leaf set-clp-transmit {
          tailf:info
            "set atm clp and send it";
          type empty;
        }
      }
    }
    container conform-set-cos-transmit {
      tailf:cli-no-keyword;
      tailf:cli-drop-node-name;
      tailf:cli-flatten-container;
      container conform-action {
        tailf:info
          "action when rate is less than conform burst";
        tailf:cli-flatten-container;
        leaf set-cos-transmit {
          tailf:info
            "rewrite packet cos and send it";
          type ncs_rpc_notif_cos_value-type;
        }
      }
    }
    container conform-set-cos-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-cos-transmit {
          tailf:info
            "rewrite packet cos and send it";
          type ncs_rpc_notif_cos_value-type;
        }
        leaf table {
          tailf:info
            "Specify table-map";
          type string;
        }
      }
    }
    container conform-set-discard-class-transmit {
      tailf:cli-no-keyword;
      tailf:cli-drop-node-name;
      tailf:cli-flatten-container;
      container conform-action {
        tailf:info
          "action when rate is less than conform burst";
        tailf:cli-flatten-container;
        leaf set-discard-class-transmit {
          tailf:info
            "set discard-class and send it";
          type uint8 {
            tailf:info
              "<0-7>;;new discard-class";
            range "0..7";
          }
        }
      }
    }
    container conform-set-dscp-transmit {
      tailf:cli-no-keyword;
      tailf:cli-drop-node-name;
      tailf:cli-flatten-container;
      container conform-action {
        tailf:info
          "action when rate is less than conform burst";
        tailf:cli-flatten-container;
        leaf set-dscp-transmit {
          tailf:info
            "set dscp and send it";
          type ncs_rpc_notif_dscp-type;
        }
      }
    }
    container conform-set-dscp-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-dscp-transmit {
          tailf:info
            "set dscp and send it";
          type ncs_rpc_notif_dscp-type;
        }
        leaf table {
          tailf:info
            "Specify table-map";
          type string;
        }
      }
    }
    container conform-set-frde-transmit {
      tailf:cli-no-keyword;
      tailf:cli-drop-node-name;
      tailf:cli-flatten-container;
      container conform-action {
        tailf:info
          "action when rate is less than conform burst";
        tailf:cli-flatten-container;
        leaf set-frde-transmit {
          tailf:info
            "set FR DE and send it";
          type empty;
        }
      }
    }
    container conform-set-mpls-exp-imposition-transmit {
      tailf:cli-no-keyword;
      tailf:cli-drop-node-name;
      tailf:cli-flatten-container;
      container conform-action {
        tailf:info
          "action when rate is less than conform burst";
        tailf:cli-flatten-container;
        leaf set-mpls-exp-imposition-transmit {
          tailf:info
            "set exp at tag imposition and send it";
          type ncs_rpc_notif_exp_value-type;
        }
      }
    }
    container conform-set-mpls-exp-imposition-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-mpls-exp-imposition-transmit {
          tailf:info
            "set exp at tag imposition and send it";
          type ncs_rpc_notif_exp_value-type;
        }
        leaf table {
          tailf:info
            "Specify table-map";
          type string;
        }
      }
    }
    container conform-set-mpls-exp-topmost-transmit {
      tailf:cli-no-keyword;
      tailf:cli-drop-node-name;
      tailf:cli-flatten-container;
      container conform-action {
        tailf:info
          "action when rate is less than conform burst";
        tailf:cli-flatten-container;
        leaf set-mpls-exp-topmost-transmit {
          tailf:info
            "set exp on topmost label and send it";
          type ncs_rpc_notif_exp_value-type;
        }
      }
    }
    container conform-set-mpls-exp-topmost-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-mpls-exp-topmost-transmit {
          tailf:info
            "set exp on topmost label and send it";
          type ncs_rpc_notif_exp_value-type;
        }
        leaf table {
          tailf:info
            "Specify table-map";
          type string;
        }
      }
    }
    container conform-set-prec-transmit {
      tailf:cli-no-keyword;
      tailf:cli-drop-node-name;
      tailf:cli-flatten-container;
      container conform-action {
        tailf:info
          "action when rate is less than conform burst";
        tailf:cli-flatten-container;
        leaf set-prec-transmit {
          tailf:info
            "rewrite packet precedence and send it";
          type ncs_rpc_notif_prec_value-type;
        }
      }
    }
    container conform-set-prec-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-prec-transmit {
          tailf:info
            "rewrite packet precedence and send it";
          type ncs_rpc_notif_prec_value-type;
        }
        leaf table {
          tailf:info
            "Specify table-map";
          type string;
        }
      }
    }
    container conform-set-qos-transmit {
      tailf:cli-no-keyword;
      tailf:cli-drop-node-name;
      tailf:cli-flatten-container;
      container conform-action {
        tailf:info
          "action when rate is less than conform burst";
        tailf:cli-flatten-container;
        leaf set-qos-transmit {
          tailf:info
            "set qos-group and send it";
          type ncs_rpc_notif_qos_value-type;
        }
      }
    }
    container conform-set-qos-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-qos-transmit {
          tailf:info
            "set qos-group and send it";
          type ncs_rpc_notif_qos_value-type;
        }
        leaf table {
          tailf:info
            "Specify table-map";
          type string;
        }
      }
    }
    container conform-transmit {
      tailf:cli-no-keyword;
      tailf:cli-drop-node-name;
      tailf:cli-flatten-container;
      container conform-action {
        tailf:info
          "action when rate is less than conform burst";
        tailf:cli-flatten-container;
        uses ncs_rpc_notif_police-action-transmit-grouping;
      }
    }
    container conform-drop {
      tailf:cli-no-keyword;
      tailf:cli-drop-node-name;
      tailf:cli-flatten-container;
      container conform-action {
        tailf:info
          "action when rate is less than conform burst";
        tailf:cli-flatten-container;
        uses ncs_rpc_notif_police-action-drop-grouping;
      }
    }
  }

  grouping ncs_rpc_notif_police-exceed-action-grouping {
    container exceed-dscp {
      tailf:cli-no-keyword;
      tailf:cli-drop-node-name;
      tailf:cli-flatten-container;
      container exceed-action {
        tailf:info
          "action when rate is within conform and conform + exceed burst";
        tailf:cli-flatten-container;
        leaf dscp {
          type ncs_rpc_notif_dscp-type;
        }
      }
    }
    container exceed-set-clp-transmit {
      tailf:cli-no-keyword;
      tailf:cli-drop-node-name;
      tailf:cli-flatten-container;
      container exceed-action {
        tailf:info
          "action when rate is within conform and conform + exceed burst";
        tailf:cli-flatten-container;
        leaf set-clp-transmit {
          tailf:info
            "set atm clp and send it";
          type empty;
        }
      }
    }
    container exceed-set-cos-transmit {
      tailf:cli-no-keyword;
      tailf:cli-drop-node-name;
      tailf:cli-flatten-container;
      container exceed-action {
        tailf:info
          "action when rate is within conform and conform + exceed burst";
        tailf:cli-flatten-container;
        leaf set-cos-transmit {
          tailf:info
            "rewrite packet cos and send it";
          type ncs_rpc_notif_cos_value-type;
        }
      }
    }
    container exceed-set-discard-class-transmit {
      tailf:cli-no-keyword;
      tailf:cli-drop-node-name;
      tailf:cli-flatten-container;
      container exceed-action {
        tailf:info
          "action when rate is within conform and conform + exceed burst";
        tailf:cli-flatten-container;
        leaf set-discard-class-transmit {
          tailf:info
            "set discard-class and send it";
          type uint8 {
            tailf:info
              "<0-7>;;new discard-class";
            range "0..7";
          }
        }
      }
    }
    container exceed-set-dscp-transmit {
      tailf:cli-no-keyword;
      tailf:cli-drop-node-name;
      tailf:cli-flatten-container;
      container exceed-action {
        tailf:info
          "action when rate is within conform and conform + exceed burst";
        tailf:cli-flatten-container;
        leaf set-dscp-transmit {
          tailf:info
            "set dscp and send it";
          type ncs_rpc_notif_dscp-type;
        }
      }
    }
    container exceed-set-frde-transmit {
      tailf:cli-no-keyword;
      tailf:cli-drop-node-name;
      tailf:cli-flatten-container;
      container exceed-action {
        tailf:info
          "action when rate is within conform and conform + exceed burst";
        tailf:cli-flatten-container;
        leaf set-frde-transmit {
          tailf:info
            "set FR DE and send it";
          type empty;
        }
      }
    }
    container exceed-set-mpls-exp-imposition-transmit {
      tailf:cli-no-keyword;
      tailf:cli-drop-node-name;
      tailf:cli-flatten-container;
      container exceed-action {
        tailf:info
          "action when rate is within conform and conform + exceed burst";
        tailf:cli-flatten-container;
        leaf set-mpls-exp-imposition-transmit {
          tailf:info
            "set exp at tag imposition and send it";
          type ncs_rpc_notif_exp_value-type;
        }
      }
    }
    container exceed-set-mpls-exp-topmost-transmit {
      tailf:cli-no-keyword;
      tailf:cli-drop-node-name;
      tailf:cli-flatten-container;
      container exceed-action {
        tailf:info
          "action when rate is within conform and conform + exceed burst";
        tailf:cli-flatten-container;
        leaf set-mpls-exp-topmost-transmit {
          tailf:info
            "set exp on topmost label and send it";
          type ncs_rpc_notif_exp_value-type;
        }
      }
    }
    container exceed-set-prec-transmit {
      tailf:cli-no-keyword;
      tailf:cli-drop-node-name;
      tailf:cli-flatten-container;
      container exceed-action {
        tailf:info
          "action when rate is within conform and conform + exceed burst";
        tailf:cli-flatten-container;
        leaf set-prec-transmit {
          tailf:info
            "rewrite packet precedence and send it";
          type ncs_rpc_notif_prec_value-type;
        }
      }
    }
    container exceed-set-qos-transmit {
      tailf:cli-no-keyword;
      tailf:cli-drop-node-name;
      tailf:cli-flatten-container;
      container exceed-action {
        tailf:info
          "action when rate is within conform and conform + exceed burst";
        tailf:cli-flatten-container;
        leaf set-qos-transmit {
          tailf:info
            "set qos-group and send it";
          type ncs_rpc_notif_qos_value-type;
        }
      }
    }
    container exceed-transmit {
      tailf:cli-no-keyword;
      tailf:cli-drop-node-name;
      tailf:cli-flatten-container;
      container exceed-action {
        tailf:info
          "action when rate is within conform and conform + exceed burst";
        tailf:cli-flatten-container;
        uses ncs_rpc_notif_police-action-transmit-grouping;
      }
    }
    container exceed-drop {
      tailf:cli-no-keyword;
      tailf:cli-drop-node-name;
      tailf:cli-flatten-container;
      container exceed-action {
        tailf:info
          "action when rate is within conform and conform + exceed burst";
        tailf:cli-flatten-container;
        uses ncs_rpc_notif_police-action-drop-grouping;
      }
    }
  }

  grouping ncs_rpc_notif_police-violate-action-grouping {
    container violate-set-clp-transmit {
      tailf:cli-no-keyword;
      tailf:cli-drop-node-name;
      tailf:cli-flatten-container;
      container violate-action {
        tailf:info
          "action when rate is greater than conform + exceed burst";
        tailf:cli-flatten-container;
        leaf set-clp-transmit {
          tailf:info
            "set atm clp and send it";
          type empty;
        }
      }
    }
    container violate-set-cos-transmit {
      tailf:cli-no-keyword;
      tailf:cli-drop-node-name;
      tailf:cli-flatten-container;
      container violate-action {
        tailf:info
          "action when rate is greater than conform + exceed burst";
        tailf:cli-flatten-container;
        leaf set-cos-transmit {
          tailf:info
            "rewrite packet cos and send it";
          type ncs_rpc_notif_cos_value-type;
        }
      }
    }
    container violate-set-discard-class-transmit {
      tailf:cli-no-keyword;
      tailf:cli-drop-node-name;
      tailf:cli-flatten-container;
      container violate-action {
        tailf:info
          "action when rate is greater than conform + exceed burst";
        tailf:cli-flatten-container;
        leaf set-discard-class-transmit {
          tailf:info
            "set discard-class and send it";
          type uint8 {
            tailf:info
              "<0-7>;;new discard-class";
            range "0..7";
          }
        }
      }
    }
    container violate-set-dscp-transmit {
      tailf:cli-no-keyword;
      tailf:cli-drop-node-name;
      tailf:cli-flatten-container;
      container violate-action {
        tailf:info
          "action when rate is greater than conform + exceed burst";
        tailf:cli-flatten-container;
        leaf set-dscp-transmit {
          tailf:info
            "set dscp and send it";
          type ncs_rpc_notif_dscp-type;
        }
      }
    }
    container violate-set-frde-transmit {
      tailf:cli-no-keyword;
      tailf:cli-drop-node-name;
      tailf:cli-flatten-container;
      container violate-action {
        tailf:info
          "action when rate is greater than conform + exceed burst";
        tailf:cli-flatten-container;
        leaf set-frde-transmit {
          tailf:info
            "set FR DE and send it";
          type empty;
        }
      }
    }
    container violate-set-mpls-exp-imposition-transmit {
      tailf:cli-no-keyword;
      tailf:cli-drop-node-name;
      tailf:cli-flatten-container;
      container violate-action {
        tailf:info
          "action when rate is greater than conform + exceed burst";
        tailf:cli-flatten-container;
        leaf set-mpls-exp-imposition-transmit {
          tailf:info
            "set exp at tag imposition and send it";
          type ncs_rpc_notif_exp_value-type;
        }
      }
    }
    container violate-set-mpls-exp-topmost-transmit {
      tailf:cli-no-keyword;
      tailf:cli-drop-node-name;
      tailf:cli-flatten-container;
      container violate-action {
        tailf:info
          "action when rate is greater than conform + exceed burst";
        tailf:cli-flatten-container;
        leaf set-mpls-exp-topmost-transmit {
          tailf:info
            "set exp on topmost label and send it";
          type ncs_rpc_notif_exp_value-type;
        }
      }
    }
    container violate-set-prec-transmit {
      tailf:cli-no-keyword;
      tailf:cli-drop-node-name;
      tailf:cli-flatten-container;
      container violate-action {
        tailf:info
          "action when rate is greater than conform + exceed burst";
        tailf:cli-flatten-container;
        leaf set-prec-transmit {
          tailf:info
            "rewrite packet precedence and send it";
          type ncs_rpc_notif_prec_value-type;
        }
      }
    }
    container violate-set-qos-transmit {
      tailf:cli-no-keyword;
      tailf:cli-drop-node-name;
      tailf:cli-flatten-container;
      container violate-action {
        tailf:info
          "action when rate is greater than conform + exceed burst";
        tailf:cli-flatten-container;
        leaf set-qos-transmit {
          tailf:info
            "set qos-group and send it";
          type ncs_rpc_notif_qos_value-type;
        }
      }
    }
    container violate-transmit {
      tailf:cli-no-keyword;
      tailf:cli-drop-node-name;
      tailf:cli-flatten-container;
      container violate-action {
        tailf:info
          "action when rate is greater than conform + exceed burst";
        tailf:cli-flatten-container;
        uses ncs_rpc_notif_police-action-transmit-grouping;
      }
    }
    container violate-drop {
      tailf:cli-no-keyword;
      tailf:cli-drop-node-name;
      tailf:cli-flatten-container;
      container violate-action {
        tailf:info
          "action when rate is greater than conform + exceed burst";
        tailf:cli-flatten-container;
        uses ncs_rpc_notif_police-action-drop-grouping;
      }
    }
  }

  grouping ncs_rpc_notif_police-action-grouping {
    container actions {
      tailf:cli-break-sequence-commands;
      tailf:cli-no-keyword;
      tailf:cli-drop-node-name;
      tailf:cli-flatten-container;
      uses ncs_rpc_notif_police-conform-action-grouping;
      uses ncs_rpc_notif_police-exceed-action-grouping;
      uses ncs_rpc_notif_police-violate-action-grouping;
    }
  }

  grouping ncs_rpc_notif_password-grouping {
    container password-container {
      tailf:cli-compact-syntax;
      tailf:cli-flatten-container;
      tailf:cli-sequence-commands;
      tailf:cli-drop-node-name;
      leaf encryption {
        tailf:cli-drop-node-name;
        tailf:cli-incomplete-command;
        tailf:cli-optional-in-sequence;
        type uint8 {
          range "0..7";
          tailf:info
            "<0-7>;;Encryption type (0 to disable encryption, 7 for proprietary)";
        }
        default "0";
      }
      leaf password {
        tailf:cli-drop-node-name;
        tailf:cli-trim-default;
        type string {
          pattern '([1-680-9a-zA-Z].*)|(0.+)|(7.+)';
          tailf:info
            "LINE;;The password";
        }
      }
    }
  }

  grouping ncs_rpc_notif_distribute-list-grouping {
    container distribute-list {
      tailf:info
        "Filter networks in routing updates";
      list accesslist {
        tailf:cli-drop-node-name;
        tailf:cli-compact-syntax;
        tailf:cli-suppress-mode;
        tailf:cli-delete-when-empty;
        tailf:cli-suppress-list-no;
        key "in-out";
        leaf in-out {
          type ncs_rpc_notif_access-list-in-out-type;
        }
      }
      list accesslist-ifname {
        tailf:cli-drop-node-name;
        tailf:cli-compact-syntax;
        tailf:cli-suppress-mode;
        tailf:cli-delete-when-empty;
        tailf:cli-suppress-list-no;
        tailf:cli-diff-dependency "/ios:interface" {
          tailf:xpath-root 3;
        }
        key "in-out interface";
        leaf in-out {
          type ncs_rpc_notif_access-list-in-out-type;
        }
        leaf interface {
          tailf:cli-expose-key-name;
          tailf:info
            "Interface";
          type string {
            tailf:info
              "WORD;;Interface name";
          }
        }
      }
      list accesslist-prefix-gateway {
        tailf:cli-drop-node-name;
        tailf:cli-compact-syntax;
        tailf:cli-suppress-mode;
        tailf:cli-delete-when-empty;
        tailf:cli-suppress-list-no;
        tailf:cli-sequence-commands;
        key "in-out";
        leaf prefix-gateway {
          tailf:cli-drop-node-name;
          tailf:cli-incomplete-command;
          mandatory true;
          tailf:cli-prefix-key;
          type enumeration {
            enum "prefix" {
              tailf:info
                "Filter prefixes in routing updates";
            }
            enum "gateway" {
              tailf:info
                "Filtering incoming updates based on gateway";
            }
          }
        }
        leaf name {
          tailf:cli-drop-node-name;
          mandatory true;
          tailf:cli-prefix-key;
          tailf:cli-disallow-value "in|out";
          type string {
            tailf:info
              "WORD;;Name of an IP prefix-list";
          }
        }
        leaf in-out {
          type ncs_rpc_notif_access-list-in-out-type;
        }
      }
      list accesslist-prefix-gateway-ifname {
        tailf:cli-drop-node-name;
        tailf:cli-compact-syntax;
        tailf:cli-suppress-mode;
        tailf:cli-delete-when-empty;
        tailf:cli-suppress-list-no;
        tailf:cli-sequence-commands;
        key "in-out interface";
        leaf prefix-gateway {
          tailf:cli-drop-node-name;
          tailf:cli-incomplete-command;
          mandatory true;
          tailf:cli-prefix-key;
          type enumeration {
            enum "prefix" {
              tailf:info
                "Filter prefixes in routing updates";
            }
            enum "gateway" {
              tailf:info
                "Filtering incoming updates based on gateway";
            }
          }
        }
        leaf name {
          tailf:cli-drop-node-name;
          mandatory true;
          tailf:cli-prefix-key;
          tailf:cli-disallow-value "in|out";
          type string {
            tailf:info
              "WORD;;Name of an IP prefix-list";
          }
        }
        leaf in-out {
          type ncs_rpc_notif_access-list-in-out-type;
        }
        leaf interface {
          tailf:cli-expose-key-name;
          tailf:info
            "Interface";
          type string {
            tailf:info
              "WORD;;Interface name";
          }
        }
      }
    }
  }

  grouping ncs_rpc_notif_passive-interface-grouping {
    container passive-interface {
      tailf:info
        "Suppress routing updates on an interface";
      choice passive-interface-choice {
        leaf default {
          tailf:info
            "Suppress routing updates on all interfaces";
          type empty;
        }
        leaf interface {
          tailf:cli-drop-node-name;
          tailf:cli-multi-value;
          type string {
            tailf:info
              "WORD;;Interface name";
          }
        }
      }
    }
    container disable {
      when '../passive-interface/default' {
        tailf:xpath-root 3;
      }
      list passive-interface {
        tailf:cli-suppress-mode;
        tailf:cli-delete-when-empty;
        tailf:cli-compact-syntax;
        key "interface";
        leaf interface {
          tailf:cli-drop-node-name;
          tailf:cli-multi-word-key;
          type string {
            tailf:info
              "WORD;;Interface name";
          }
        }
      }
    }
  }

  grouping ncs_rpc_notif_interface-grouping {
    choice interface-choice {
      leaf Embedded-Service-Engine {
        tailf:info
          "cisco embedded service engine module";
        tailf:cli-allow-join-with-value {
          tailf:cli-display-joined;
        }
        type string;
        // NCS drop tailf-common:non-strict-leafref statement
      }
      leaf FastEthernet {
        tailf:info
          "FastEthernet IEEE 802.3";
        tailf:cli-allow-join-with-value {
          tailf:cli-display-joined;
        }
        type string;
        // NCS drop tailf-common:non-strict-leafref statement
      }
      leaf GigabitEthernet {
        tailf:info
          "GigabitEthernet IEEE 802.3z";
        tailf:cli-allow-join-with-value {
          tailf:cli-display-joined;
        }
        type string;
        // NCS drop tailf-common:non-strict-leafref statement
      }
      leaf Loopback {
        tailf:info
          "Loopback interface";
        tailf:cli-allow-join-with-value {
          tailf:cli-display-joined;
        }
        type string;
        // NCS drop tailf-common:non-strict-leafref statement
      }
      leaf Multilink {
        tailf:info
          "Multilink-group interface";
        tailf:cli-allow-join-with-value {
          tailf:cli-display-joined;
        }
        type uint16;
        // NCS drop tailf-common:non-strict-leafref statement
      }
      leaf Port-channel {
        tailf:info
          "Ethernet Channel of interfaces";
        tailf:cli-allow-join-with-value {
          tailf:cli-display-joined;
        }
        type uint32;
        // NCS drop tailf-common:non-strict-leafref statement
      }
      leaf Serial {
        tailf:info
          "Serial interface";
        tailf:cli-allow-join-with-value {
          tailf:cli-display-joined;
        }
        type string;
        // NCS drop tailf-common:non-strict-leafref statement
      }
      leaf TenGigabitEthernet {
        tailf:info
          "Ten Gigabit Ethernet";
        tailf:cli-allow-join-with-value {
          tailf:cli-display-joined;
        }
        type string;
        // NCS drop tailf-common:non-strict-leafref statement
      }
      leaf Virtual-Template {
        tailf:info
          "Virtual Template interface";
        tailf:cli-allow-join-with-value {
          tailf:cli-display-joined;
        }
        type uint16 {
          tailf:info
            "<1-4095>;;Virtual-Template interface number";
        }
        // NCS drop tailf-common:non-strict-leafref statement
      }
      leaf Vlan {
        tailf:info
          "Iosxr Vlans";
        tailf:cli-allow-join-with-value {
          tailf:cli-display-joined;
        }
        type uint16;
        // NCS drop tailf-common:non-strict-leafref statement
      }
    }
  }

  grouping ncs_rpc_notif_ethernet-grouping {
    choice ethernet-choice {
      leaf FastEthernet {
        tailf:info
          "FastEthernet IEEE 802.3";
        tailf:cli-allow-join-with-value {
          tailf:cli-display-joined;
        }
        type string;
        // NCS drop tailf-common:non-strict-leafref statement
      }
      leaf GigabitEthernet {
        tailf:info
          "GigabitEthernet IEEE 802.3z";
        tailf:cli-allow-join-with-value {
          tailf:cli-display-joined;
        }
        type string;
        // NCS drop tailf-common:non-strict-leafref statement
      }
      leaf Port-channel {
        tailf:info
          "Ethernet Channel of interfaces";
        tailf:cli-allow-join-with-value {
          tailf:cli-display-joined;
        }
        type uint32;
        // NCS drop tailf-common:non-strict-leafref statement
      }
      leaf TenGigabitEthernet {
        tailf:info
          "Ten Gigabit Ethernet";
        tailf:cli-allow-join-with-value {
          tailf:cli-display-joined;
        }
        type string;
        // NCS drop tailf-common:non-strict-leafref statement
      }
    }
  }

  grouping ncs_rpc_notif_ip-community-list-standard-grouping {
    container deny {
      tailf:info
        "Specify community to reject";
      presence "Specify community to reject";
      list deny-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local\-AS)|(no\-advertise)|(no\-export)|(\d+:\d+)|(\d+))( (internet)|(local\-AS)|(no\-advertise)|(no\-export)|(\d+:\d+)|(\d+))*';
          }
        }
      }
    }
    container permit {
      tailf:info
        "Specify community to accept";
      presence "Specify community to accept";
      list permit-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local-AS)|(no-advertise)|(no-export)|(\d+:\d+)|(\d+))( (internet)|(local-AS)|(no-advertise)|(no-export)|(\d+:\d+)|(\d+))*';
          }
        }
      }
    }
  }

  grouping ncs_rpc_notif_ip-community-list-expanded-grouping {
    container deny {
      tailf:info
        "Specify community to reject";
      presence "Specify community to reject";
      list deny-list {
        tailf:cli-suppress-mode;
        tailf:cli-delete-when-empty;
        tailf:cli-drop-node-name;
        key "expr";
        leaf expr {
          tailf:info
            "LINE;;An ordered list as a regular-expression";
          tailf:cli-multi-word-key {
            tailf:cli-max-words 10;
          }
          type string;
        }
      }
    }
    container permit {
      tailf:info
        "Specify community to accept";
      presence "Specify community to accept";
      list permit-list {
        tailf:cli-suppress-mode;
        tailf:cli-delete-when-empty;
        tailf:cli-drop-node-name;
        key "expr";
        leaf expr {
          tailf:info
            "LINE;;An ordered list as a regular-expression";
          tailf:cli-multi-word-key {
            tailf:cli-max-words 10;
          }
          type string;
        }
      }
    }
  }

  grouping ncs_rpc_notif_ip-route-options-grouping {
    leaf metric {
      tailf:cli-drop-node-name;
      tailf:cli-break-sequence-commands;
      type uint8 {
        tailf:info
          "<1-255>;;Distance metric for this route";
        range "1..255";
      }
    }
    leaf global {
      tailf:info
        "Next hop address is global";
      type empty;
    }
    leaf name {
      tailf:info
        "Specify name of the next hop";
      type string {
        tailf:info
          "WORD;;Name of the next hop";
      }
    }
    leaf permanent {
      tailf:info
        "permanent route";
      type empty;
    }
    leaf multicast {
      tailf:info
        "multicast route";
      type empty;
    }
    leaf dhcp {
      tailf:info
        "Default Gateway obtained from DHCP";
      tailf:cli-case-insensitive;
      type empty;
    }
    leaf tag {
      tailf:info
        "Set tag for this route";
      type uint32 {
        tailf:info
          "<1-4294967295>;;Tag value";
        range "1..4294967295";
      }
    }
    leaf track {
      tailf:info
        "Install route depending on tracked item";
      type uint16 {
        tailf:info
          "<1-500>;;tracked object number";
        range "1..500";
      }
    }
  }

  grouping ncs_rpc_notif_ip-route-grouping {
    list ip-route-interface-forwarding-list {
      tailf:cli-drop-node-name;
      tailf:cli-suppress-mode;
      tailf:cli-delete-when-empty;
      tailf:cli-compact-syntax;
      tailf:cli-sequence-commands {
        tailf:cli-reset-all-siblings;
      }
      key "prefix mask interface forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-diff-dependency "/ios:interface" {
          tailf:xpath-root 3;
        }
        type string {
          tailf:info
            "WORD;;Interface name";
        }
      }
      leaf forwarding-address {
        type union {
          type inet:ipv4-address {
            tailf:info
              "A.B.C.D;;Forwarding router's address";
          }
          type enumeration {
            enum "multicast" {
              tailf:info
                "multicast route";
            }
          }
        }
      }
      uses ncs_rpc_notif_ip-route-options-grouping;
    }
    list ip-route-forwarding-list {
      tailf:cli-drop-node-name;
      tailf:cli-suppress-mode;
      tailf:cli-delete-when-empty;
      tailf:cli-compact-syntax;
      tailf:cli-sequence-commands {
        tailf:cli-reset-all-siblings;
      }
      key "prefix mask forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf forwarding-address {
        type inet:ipv4-address {
          tailf:info
            "A.B.C.D;;Forwarding router's address";
        }
      }
      uses ncs_rpc_notif_ip-route-options-grouping;
    }
    list ip-route-interface-list {
      tailf:cli-drop-node-name;
      tailf:cli-suppress-mode;
      tailf:cli-delete-when-empty;
      tailf:cli-compact-syntax;
      tailf:cli-sequence-commands {
        tailf:cli-reset-all-siblings;
      }
      key "prefix mask interface";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-diff-dependency "/ios:interface" {
          tailf:xpath-root 3;
        }
        tailf:cli-case-insensitive;
        type union {
          type string {
            tailf:info
              "WORD;;Interface name";
          }
          type enumeration {
            enum "dhcp" {
              tailf:info
                "Default Gateway obtained from DHCP";
            }
          }
        }
      }
      uses ncs_rpc_notif_ip-route-options-grouping;
    }
  }

  grouping ncs_rpc_notif_ipv6-route-options-grouping {
    leaf distance {
      tailf:cli-drop-node-name;
      type uint8 {
        tailf:info
          "<1-254>;;Administrative distance";
      }
    }
    choice type-choice {
      leaf multicast {
        tailf:info
          "Route only usable by multicast";
        tailf:cli-full-command;
        type empty;
      }
      leaf unicast {
        tailf:info
          "Route only usable by unicast";
        type empty;
      }
    }
    leaf tag {
      tailf:info
        "Tag value";
      tailf:cli-full-command;
      type uint32 {
        tailf:info
          "<0-4294967295>  Tag value";
      }
    }
  }

  grouping ncs_rpc_notif_ipv6-route-entry-grouping {
    list ipv6-destination-list {
      tailf:cli-drop-node-name;
      tailf:cli-suppress-mode;
      tailf:cli-delete-when-empty;
      tailf:cli-compact-syntax;
      tailf:cli-reset-container;
      key "destination";
      leaf destination {
        type inet:ipv6-address {
          tailf:info
            "X:X:X:X::X;;IPv6 address of next-hop";
        }
      }
      uses ncs_rpc_notif_ipv6-route-options-grouping;
    }
  }

  grouping ncs_rpc_notif_ipv6-route-grouping {
    list ipv6-route-list {
      tailf:cli-drop-node-name;
      tailf:cli-suppress-mode;
      tailf:cli-delete-when-empty;
      tailf:cli-compact-syntax;
      tailf:cli-reset-container;
      tailf:cli-incomplete-command;
      key "prefix";
      leaf prefix {
        type ncs_rpc_notif_ipv6-prefix;
      }
      uses ncs_rpc_notif_ipv6-route-entry-grouping;
      list FastEthernet {
        tailf:info
          "FastEthernet IEEE 802.3";
        tailf:cli-allow-join-with-key {
          tailf:cli-display-joined;
        }
        tailf:cli-suppress-mode;
        tailf:cli-delete-when-empty;
        tailf:cli-compact-syntax;
        tailf:cli-reset-container;
        key "name";
        leaf name {
          type string {
            tailf:info
              "<0-66>/<0-128>;;FastEthernet interface number";
          }
        }
        uses ncs_rpc_notif_ipv6-route-entry-grouping;
        uses ncs_rpc_notif_ipv6-route-options-grouping;
      }
      list Null {
        tailf:info
          "Null interface";
        tailf:cli-allow-join-with-key {
          tailf:cli-display-joined;
        }
        tailf:cli-suppress-mode;
        tailf:cli-delete-when-empty;
        tailf:cli-compact-syntax;
        tailf:cli-reset-container;
        key "name";
        leaf name {
          type enumeration {
            enum "0" {
              tailf:info
                "<0-0>;;Null interface number";
            }
          }
        }
        uses ncs_rpc_notif_ipv6-route-entry-grouping;
        uses ncs_rpc_notif_ipv6-route-options-grouping;
      }
    }
  }

  grouping ncs_rpc_notif_random-detect-grouping {
    leaf min-threshold {
      tailf:cli-drop-node-name;
      tailf:cli-incomplete-command;
      type uint16 {
        range "1..4096";
        tailf:info
          "<1-4096>;;minimum threshold (number of packets)";
      }
    }
    leaf max-threshold {
      tailf:cli-drop-node-name;
      tailf:cli-incomplete-command;
      type uint16 {
        range "1..4096";
        tailf:info
          "<1-4096>;;maximum threshold (number of packets)";
      }
    }
    leaf denominator {
      tailf:cli-drop-node-name;
      type uint32 {
        range "1..65535";
        tailf:info
          "<1-65535>;;mark probability denominator";
      }
    }
  }

  grouping ncs_rpc_notif_class-map-match-grouping {
    container access-group {
      tailf:info
        "Access group";
      leaf index {
        tailf:cli-drop-node-name;
        type uint32 {
          range "1..2699" {
            tailf:info
              "<1-2699>;;Access list index";
          }
        }
      }
      leaf-list name {
        tailf:info
          "Named Access List";
        tailf:cli-list-syntax;
        type string {
          tailf:info
            "WORD;;Access List name";
        }
      }
    }
    leaf any {
      tailf:info
        "Any packets";
      type empty;
    }
    leaf-list class-map {
      tailf:info
        "Class map";
      tailf:cli-list-syntax;
      type string;
    }
    leaf-list cos {
      tailf:info
        "IEEE 802.1Q/ISL class of service/user priority values";
      tailf:cli-flat-list-syntax;
      type uint16 {
        range "0..7";
        tailf:info
          "<0-7>;;Enter up to 4 class-of-service values separated by white-spaces";
      }
    }
    container destination-address {
      tailf:info
        "Destination address";
      leaf-list mac {
        tailf:info
          "MAC address";
        tailf:cli-list-syntax;
        type string {
          tailf:info
            "H.H.H;;MAC address";
        }
      }
    }
    leaf-list discard-class {
      tailf:info
        "Discard behavior identifier";
      tailf:cli-list-syntax;
      type uint16 {
        range "0..7";
        tailf:info
          "<0-7>;;Discard Class value";
      }
    }
    leaf-list dscp {
      tailf:info
        "Match DSCP in IP(v4) and IPv6 packets";
      tailf:cli-list-syntax;
      type ncs_rpc_notif_dscp-type;
    }
    leaf fr-de {
      tailf:info
        "Match on Frame-relay DE bit";
      type empty;
    }
    leaf-list fr-dlci {
      tailf:info
        "Match on fr-dlci";
      tailf:cli-list-syntax;
      type uint16 {
        range "16..1007";
        tailf:info
          "<16-1007>;;frame-relay dlci number";
      }
    }
    leaf-list input-interface {
      tailf:info
        "Select an input interface to match";
      tailf:cli-list-syntax;
      type string;
    }
    container ip {
      tailf:info
        "IP specific values";
      leaf-list dscp {
        tailf:info
          "Match IP DSCP (DiffServ CodePoints)";
        tailf:cli-flat-list-syntax;
        type ncs_rpc_notif_dscp-type;
      }
      leaf-list precedence {
        tailf:info
          "Match IP precedence";
        tailf:cli-flat-list-syntax;
        type ncs_rpc_notif_precedence-type;
      }
      list rtp {
        tailf:info
          "Match RTP port nos";
        key "port1 port2";
        leaf port1 {
          type uint16 {
            range "2000..65535";
            tailf:info
              "<2000-65535>;;Lower bound of UDP destination port";
          }
        }
        leaf port2 {
          type uint16 {
            range "0..16383";
            tailf:info
              "<0-16383>;;Range of UDP ports";
          }
        }
      }
    }
    container mpls {
      tailf:info
        "Multi Protocol Label Switching specific values";
      container experimental {
        tailf:info
          "Match MPLS experimental";
        leaf-list topmost {
          tailf:info
            "Match MPLS experimental value on topmost label";
          tailf:cli-flat-list-syntax;
          type uint16 {
            range "0..7";
            tailf:info
              "<0-7>;;Enter up to 8 experimental values separated by white-spaces";
          }
        }
      }
    }
    container packet {
      tailf:info
        "Layer 3 Packet length";
      container length {
        tailf:info
          "Layer 3 Packet length";
        leaf max {
          tailf:info
            "Maximum length of packet";
          type uint16 {
            range "1..2000";
            tailf:info
              "<1-2000>;;Packet length in bytes";
          }
        }
        leaf min {
          tailf:info
            "Minimum length of packet";
          type uint16 {
            range "1..2000";
            tailf:info
              "<1-2000>;;Packet length in bytes";
          }
        }
      }
    }
    leaf-list precedence {
      tailf:info
        "Match Precedence in IP(v4) and IPv6 packets";
      tailf:cli-flat-list-syntax;
      type ncs_rpc_notif_precedence-type;
    }
    container protocol {
      tailf:info
        "Protocol";
      leaf x802-11-iapp {
        tailf:info
          "IEEE 802.11 WLANs WG IAPP";
        tailf:alt-name "802-11-iapp";
        type empty;
      }
      leaf ace-svr {
        tailf:info
          "ACE Server/Propagation";
        type empty;
      }
      leaf aol {
        tailf:info
          "America-Online Instant Messenger";
        type empty;
      }
      leaf appleqtc {
        tailf:info
          "Apple QuickTime";
        type empty;
      }
      leaf biff {
        tailf:info
          "Bliff mail notification";
        type empty;
      }
      leaf bittorrent {
        tailf:info
          "bittorrent";
        type empty;
      }
      leaf bootpc {
        tailf:info
          "Bootstrap Protocol Client";
        type empty;
      }
      leaf bootps {
        tailf:info
          "Bootstrap Protocol Server";
        type empty;
      }
      leaf cddbp {
        tailf:info
          "CD Database Protocol";
        type empty;
      }
      leaf cifs {
        tailf:info
          "CIFS";
        type empty;
      }
      leaf cisco-fna {
        tailf:info
          "Cisco FNATIVE";
        type empty;
      }
      leaf cisco-net-mgmt {
        tailf:info
          "cisco-net-mgmt";
        type empty;
      }
      leaf cisco-svcs {
        tailf:info
          "cisco license/perf/GDP/X.25/ident svcs";
        type empty;
      }
      leaf cisco-sys {
        tailf:info
          "Cisco SYSMAINT";
        type empty;
      }
      leaf cisco-tdp {
        tailf:info
          "Cisco TDP";
        type empty;
      }
      leaf cisco-tna {
        tailf:info
          "Cisco TNATIVE";
        type empty;
      }
      leaf citriximaclient {
        tailf:info
          "Citrix IMA Client";
        type empty;
      }
      leaf clp {
        tailf:info
          "Cisco Line Protocol";
        type empty;
      }
      leaf creativepartnr {
        tailf:info
          "Creative Partnr";
        type empty;
      }
      leaf creativeserver {
        tailf:info
          "Creative Server";
        type empty;
      }
      leaf daytime {
        tailf:info
          "Daytime (RFC 867)";
        type empty;
      }
      leaf dbase {
        tailf:info
          "dBASE Unix";
        type empty;
      }
      leaf dbcontrol_agent {
        tailf:info
          "Oracle dbControl Agent po";
        type empty;
      }
      leaf ddns-v3 {
        tailf:info
          "Dynamic DNS Version 3";
        type empty;
      }
      leaf dhcp-failover {
        tailf:info
          "DHCP Failover";
        type empty;
      }
      leaf directconnect {
        tailf:info
          "Direct Connect Version 2.0";
        type empty;
      }
      leaf discard {
        tailf:info
          "Discard port";
        type empty;
      }
      leaf dnsix {
        tailf:info
          "DNSIX Securit Attribute Token Map";
        type empty;
      }
      leaf echo {
        tailf:info
          "Echo port";
        type empty;
      }
      leaf entrust-svc-hdlr {
        tailf:info
          "Entrust KM/Admin Service Handler";
        type empty;
      }
      leaf entrust-svcs {
        tailf:info
          "Entrust sps/aaas/aams";
        type empty;
      }
      leaf exec {
        tailf:info
          "Remote Process Execution";
        type empty;
      }
      leaf fcip-port {
        tailf:info
          "FCIP";
        type empty;
      }
      leaf ftps {
        tailf:info
          "FTP over TLS/SSL";
        type empty;
      }
      leaf gdoi {
        tailf:info
          "GDOI";
        type empty;
      }
      leaf giop {
        tailf:info
          "Oracle GIOP/SSL";
        type empty;
      }
      leaf gtpv0 {
        tailf:info
          "GPRS Tunneling Protocol Version 0";
        type empty;
      }
      leaf gtpv1 {
        tailf:info
          "GPRS Tunneling Protocol Version 1";
        type empty;
      }
      leaf h225ras {
        tailf:info
          "H225 RAS over Unicast";
        type empty;
      }
      leaf h323callsigalt {
        tailf:info
          "h323 Call Signal Alternate";
        type empty;
      }
      leaf hp-alarm-mgr {
        tailf:info
          "HP Performance data alarm manager";
        type empty;
      }
      leaf hp-collector {
        tailf:info
          "HP Performance data collector";
        type empty;
      }
      leaf hp-managed-node {
        tailf:info
          "HP Performance data managed node";
        type empty;
      }
      leaf hsrp {
        tailf:info
          "Hot Standby Router Protocol";
        type empty;
      }
      leaf https {
        tailf:info
          "Secure Hypertext Transfer Protocol";
        type empty;
      }
      leaf ica {
        tailf:info
          "ica (Citrix)";
        type empty;
      }
      leaf icabrowser {
        tailf:info
          "icabrowser (Citrix)";
        type empty;
      }
      leaf ident {
        tailf:info
          "Authentication Service";
        type empty;
      }
      leaf igmpv3lite {
        tailf:info
          "IGMP over UDP for SSM";
        type empty;
      }
      leaf imap3 {
        tailf:info
          "Interactive Mail Access Protocol 3";
        type empty;
      }
      leaf imaps {
        tailf:info
          "IMAP over TLS/SSL";
        type empty;
      }
      leaf ipass {
        tailf:info
          "IPASS";
        type empty;
      }
      leaf ipsec-msft {
        tailf:info
          "Microsoft IPsec NAT-T";
        type empty;
      }
      leaf irc-serv {
        tailf:info
          "IRC-SERV";
        type empty;
      }
      leaf ircs {
        tailf:info
          "IRC over TLS/SSL";
        type empty;
      }
      leaf ircu {
        tailf:info
          "IRCU";
        type empty;
      }
      leaf isakmp {
        tailf:info
          "ISAKMP";
        type empty;
      }
      leaf iscsi {
        tailf:info
          "iSCSI";
        type empty;
      }
      leaf iscsi-target {
        tailf:info
          "iSCSI port";
        type empty;
      }
      leaf kermit {
        tailf:info
          "kermit";
        type empty;
      }
      leaf ldap-admin {
        tailf:info
          "LDAP admin server port";
        type empty;
      }
      leaf ldaps {
        tailf:info
          "LDAP over TLS/SSL";
        type empty;
      }
      leaf login {
        tailf:info
          "Remote login";
        type empty;
      }
      leaf lotusmtap {
        tailf:info
          "Lotus Mail Tracking Agent Protocol";
        type empty;
      }
      leaf lotusnote {
        tailf:info
          "Lotus Note";
        type empty;
      }
      leaf microsoft-ds {
        tailf:info
          "Microsoft-DS";
        type empty;
      }
      leaf ms-cluster-net {
        tailf:info
          "MS Cluster Net";
        type empty;
      }
      leaf ms-dotnetster {
        tailf:info
          "Microsoft .NETster Port";
        type empty;
      }
      leaf ms-sna {
        tailf:info
          "Microsoft SNA Server/Base";
        type empty;
      }
      leaf ms-sql {
        tailf:info
          "Microsoft SQL";
        type empty;
      }
      leaf ms-sql-m {
        tailf:info
          "Microsoft SQL Monitor";
        type empty;
      }
      leaf msexch-routing {
        tailf:info
          "Microsoft Exchange Routing";
        type empty;
      }
      leaf msnmsgr {
        tailf:info
          "MSN Instant Messenger";
        type empty;
      }
      leaf msrpc {
        tailf:info
          "Microsoft Remote Procedure Call";
        type empty;
      }
      leaf mysql {
        tailf:info
          "MySQL";
        type empty;
      }
      leaf n2h2server {
        tailf:info
          "N2H2 Filter Service Port";
        type empty;
      }
      leaf ncp {
        tailf:info
          "NCP (Novell)";
        type empty;
      }
      leaf net8-cman {
        tailf:info
          "Oracle Net8 Cman/Admin";
        type empty;
      }
      leaf netbios-dgm {
        tailf:info
          "NETBIOS Datagram Service";
        type empty;
      }
      leaf netbios-ns {
        tailf:info
          "NETBIOS Name Service";
        type empty;
      }
      leaf netbios-ssn {
        tailf:info
          "NETBIOS Session Service";
        type empty;
      }
      leaf netstat {
        tailf:info
          "Variant of systat";
        type empty;
      }
      leaf oem-agent {
        tailf:info
          "OEM Agent (Oracle)";
        type empty;
      }
      leaf oracle {
        tailf:info
          "Oracle";
        type empty;
      }
      leaf oracle-em-vp {
        tailf:info
          "Oracle EM/VP";
        type empty;
      }
      leaf oraclenames {
        tailf:info
          "Oracle Names";
        type empty;
      }
      leaf orasrv {
        tailf:info
          "Oracle SQL*Net v1/v2";
        type empty;
      }
      leaf pcanywheredata {
        tailf:info
          "pcANYWHEREdata";
        type empty;
      }
      leaf pcanywherestat {
        tailf:info
          "pcANYWHEREstat";
        type empty;
      }
      leaf pop3s {
        tailf:info
          "POP3 over TLS/SSL";
        type empty;
      }
      leaf pwdgen {
        tailf:info
          "Password  Generator Protocol";
        type empty;
      }
      leaf qmtp {
        tailf:info
          "Quick Mail Transfer Protocol";
        type empty;
      }
      leaf r-winsock {
        tailf:info
          "remote-winsock";
        type empty;
      }
      leaf radius {
        tailf:info
          "RADIUS & Accounting";
        type empty;
      }
      leaf rdb-dbs-disp {
        tailf:info
          "Oracle RDB";
        type empty;
      }
      leaf realmedia {
        tailf:info
          "RealNetwork's Realmedia Protocol";
        type empty;
      }
      leaf realsecure {
        tailf:info
          "ISS Real Secure Console Service Port";
        type empty;
      }
      leaf router {
        tailf:info
          "Local Routing Process";
        type empty;
      }
      leaf rsvp-encap {
        tailf:info
          "RSVP ENCAPSULATION-1/2";
        type empty;
      }
      leaf rsvp_tunnel {
        tailf:info
          "RSVP Tunnel";
        type empty;
      }
      leaf rtc-pm-port {
        tailf:info
          "Oracle RTC-PM port";
        type empty;
      }
      leaf rtelnet {
        tailf:info
          "Remote Telnet Service";
        type empty;
      }
      leaf send {
        tailf:info
          "SEND";
        type empty;
      }
      leaf shell {
        tailf:info
          "Remote command";
        type empty;
      }
      leaf sip-tls {
        tailf:info
          "SIP-TLS";
        type empty;
      }
      leaf sms {
        tailf:info
          "SMS RCINFO/XFER/CHAT";
        type empty;
      }
      leaf snmptrap {
        tailf:info
          "SNMP Trap";
        type empty;
      }
      leaf sql-net {
        tailf:info
          "SQL-NET";
        type empty;
      }
      leaf sqlserv {
        tailf:info
          "SQL Services";
        type empty;
      }
      leaf sqlsrv {
        tailf:info
          "SQL Service";
        type empty;
      }
      leaf sshell {
        tailf:info
          "SSLshell";
        type empty;
      }
      leaf ssp {
        tailf:info
          "State Sync Protocol";
        type empty;
      }
      leaf syslog-conn {
        tailf:info
          "Reliable Syslog Service";
        type empty;
      }
      leaf tacacs {
        tailf:info
          "Login Host Protocol (TACACS)";
        type empty;
      }
      leaf tacacs-ds {
        tailf:info
          "TACACS-Database Service";
        type empty;
      }
      leaf tarantella {
        tailf:info
          "Tarantella";
        type empty;
      }
      leaf tcp {
        tailf:info
          "TCP";
        type empty;
      }
      leaf telnets {
        tailf:info
          "Telnet over TLS/SSL";
        type empty;
      }
      leaf time {
        tailf:info
          "Time";
        type empty;
      }
      leaf timed {
        tailf:info
          "Time server";
        type empty;
      }
      leaf tr-rsrb {
        tailf:info
          "cisco RSRB";
        type empty;
      }
      leaf ttc {
        tailf:info
          "Oracle TTC/SSL";
        type empty;
      }
      leaf udp {
        tailf:info
          "UDP";
        type empty;
      }
      leaf uucp {
        tailf:info
          "UUCPD/UUCP-RLOGIN";
        type empty;
      }
      leaf vqp {
        tailf:info
          "VQP";
        type empty;
      }
      leaf webster {
        tailf:info
          "Network Disctionary";
        type empty;
      }
      leaf who {
        tailf:info
          "Who's service";
        type empty;
      }
      leaf wins {
        tailf:info
          "Microsoft WINS";
        type empty;
      }
      leaf x11 {
        tailf:info
          "X Window System";
        type empty;
      }
      leaf xdmcp {
        tailf:info
          "XDM Control Protocol";
        type empty;
      }
      leaf ymsgr {
        tailf:info
          "Yahoo! Instant Messenger";
        type empty;
      }
      leaf aarp {
        tailf:info
          "AppleTalk ARP";
        type empty;
      }
      leaf appletalk {
        tailf:info
          "AppleTalk";
        type empty;
      }
      leaf arp {
        tailf:info
          "IP ARP";
        type empty;
      }
      leaf bgp {
        tailf:info
          "Border Gateway Protocol";
        type empty;
      }
      leaf bridge {
        tailf:info
          "Bridging";
        type empty;
      }
      leaf bstun {
        tailf:info
          "Block Serial Tunnel";
        type empty;
      }
      leaf cdp {
        tailf:info
          "Cisco Discovery Protocol";
        type empty;
      }
      container citrix {
        tailf:info
          "Citrix Systems ICA protocol";
        presence "enable citrix system protocol matching";
        leaf ica-tag {
          tailf:info
            "Citrix ICA tag 0-high 1-medium 2-low 3-background";
          type string {
            tailf:info
              "WORD;;Enter a string as the sub-protocol parameter";
          }
        }
      }
      leaf clns {
        tailf:info
          "ISO CLNS";
        type empty;
      }
      leaf clns_es {
        tailf:info
          "ISO CLNS End System";
        type empty;
      }
      leaf clns_is {
        tailf:info
          "ISO CLNS Intermediate System";
        type empty;
      }
      leaf cmns {
        tailf:info
          "ISO CMNS";
        type empty;
      }
      leaf compressedtcp {
        tailf:info
          "Compressed TCP (VJ";
        type empty;
      }
      leaf cuseeme {
        tailf:info
          "CU-SeeMe desktop video conference";
        type empty;
      }
      leaf decnet {
        tailf:info
          "DECnet";
        type empty;
      }
      leaf decnet_node {
        tailf:info
          "DECnet Node";
        type empty;
      }
      leaf decnet_router-l1 {
        tailf:info
          "DECnet Router L1";
        type empty;
      }
      leaf decnet_router-l2 {
        tailf:info
          "DECnet Router L2";
        type empty;
      }
      leaf dhcp {
        tailf:info
          "Dynamic Host Configuration";
        type empty;
      }
      leaf dlsw {
        type empty;
        tailf:info
          "Data Link Switching (Direct encapsulation only";
      }
      leaf dns {
        type empty;
        tailf:info
          "Domain Name Server lookup";
      }
      leaf edonkey {
        type empty;
        tailf:info
          "eDonkey";
      }
      leaf egp {
        type empty;
        tailf:info
          "Exterior Gateway Protocol";
      }
      leaf eigrp {
        type empty;
        tailf:info
          "Enhanced Interior Gateway Routing Protocol";
      }
      leaf exchange {
        type empty;
        tailf:info
          "MS-RPC for Exchange";
      }
      container fasttrack {
        tailf:info
          "FastTrack Traffic - KaZaA, Morpheus, Grokster";
        presence "enable fasttrack matching";
        leaf file-transfer {
          tailf:info
            "File transfer stream";
          type string {
            tailf:info
              "WORD;;Enter a string as the sub-protocol parameter";
          }
        }
      }
      leaf finger {
        type empty;
        tailf:info
          "Finger";
      }
      leaf ftp {
        type empty;
        tailf:info
          "File Transfer Protocol";
      }
      container gnutella {
        tailf:info
          "Gnutella Version2 Traffic - BearShare, Shareeza, Morpheus";
        presence "enable gnutella matching";
        leaf file-transfer {
          tailf:info
            "File transfer stream";
          type string {
            tailf:info
              "WORD;;Enter a string as the sub-protocol parameter";
          }
        }
      }
      leaf gopher {
        type empty;
        tailf:info
          "Gopher";
      }
      leaf gre {
        type empty;
        tailf:info
          "Generic Routing Encapsulation";
      }
      leaf h323 {
        type empty;
        tailf:info
          "H323 Protocol";
      }
      container http {
        tailf:info
          "World Wide Web traffic";
        presence "enable http traffic matching";
        leaf c-header-field {
          tailf:info
            "Client general Header Field";
          type string {
            tailf:info
              "WORD;;Enter a string as the sub-protocol parameter";
          }
        }
        leaf host {
          tailf:info
            "Server Host Name";
          type string {
            tailf:info
              "WORD;;Enter a string as the sub-protocol parameter";
          }
        }
        leaf mime {
          tailf:info
            "Match MIME Type";
          type string {
            tailf:info
              "WORD;;Enter a string as the sub-protocol parameter";
          }
        }
        leaf s-header-field {
          tailf:info
            "Server general Header Field";
          type string {
            tailf:info
              "WORD;;Enter a string as the sub-protocol parameter";
          }
        }
        leaf url {
          tailf:info
            "Match URL String";
          type string {
            tailf:info
              "WORD;;Enter a string as the sub-protocol parameter";
          }
        }
      }
      leaf icmp {
        tailf:info
          "Internet Control Message";
        type empty;
      }
      leaf imap {
        tailf:info
          "Internet Message Access Protocol";
        type empty;
      }
      leaf ip {
        tailf:info
          "IP";
        type empty;
      }
      leaf ipinip {
        tailf:info
          "IP in IP (encapsulation";
        type empty;
      }
      leaf ipsec {
        tailf:info
          "IP Security Protocol (ESP/AH";
        type empty;
      }
      leaf ipv6 {
        tailf:info
          "IPV6";
        type empty;
      }
      leaf ipx {
        tailf:info
          "Novell IPX";
        type empty;
      }
      leaf irc {
        type empty;
        tailf:info
          "Internet Relay Chat";
      }
      container kazaa2 {
        tailf:info
          "Kazaa Version 2";
        presence "enable kazaa version 2 matching";
        leaf file-transfer {
          tailf:info
            "File transfer stream";
          type string {
            tailf:info
              "WORD;;Enter a string as the sub-protocol parameter";
          }
        }
      }
      leaf kerberos {
        tailf:info
          "Kerberos";
        type empty;
      }
      leaf l2tp {
        tailf:info
          "L2F/L2TP tunnel";
        type empty;
      }
      leaf ldap {
        tailf:info
          "Lightweight Directory Access Protocol";
        type empty;
      }
      leaf llc2 {
        tailf:info
          "llc2";
        type empty;
      }
      leaf mgcp {
        tailf:info
          "Media Gateway Control Protocol";
        type empty;
      }
      container napster {
        tailf:info
          "Napster Traffic";
        presence "enable napster matching";
        leaf non-std {
          tailf:info
            "Non-standard port advertizements";
          type empty;
        }
      }
      leaf netbios {
        tailf:info
          "NetBIOS";
        type empty;
      }
      leaf netshow {
        tailf:info
          "Microsoft Netshow";
        type empty;
      }
      leaf nfs {
        tailf:info
          "Network File System";
        type empty;
      }
      leaf nntp {
        tailf:info
          "Network News Transfer Protocol";
        type empty;
      }
      leaf notes {
        tailf:info
          "Lotus Notes(R";
        type empty;
      }
      leaf novadigm {
        tailf:info
          "Novadigm EDM";
        type empty;
      }
      leaf ntp {
        tailf:info
          "Network Time Protocol";
        type empty;
      }
      leaf ospf {
        tailf:info
          "Open Shortest Path First";
        type empty;
      }
      leaf pad {
        tailf:info
          "PAD links";
        type empty;
      }
      leaf pcanywhere {
        tailf:info
          "Symantec pcANYWHERE";
        type empty;
      }
      leaf pop3 {
        tailf:info
          "Post Office Protocol";
        type empty;
      }
      leaf pppoe {
        tailf:info
          "PPP over Ethernet";
        type empty;
      }
      leaf pptp {
        tailf:info
          "Point-to-Point Tunneling Protocol";
        type empty;
      }
      leaf printer {
        tailf:info
          "print spooler/lpd";
        type empty;
      }
      leaf qllc {
        tailf:info
          "qllc protocol";
        type empty;
      }
      leaf rcmd {
        tailf:info
          "BSD r-commands (rsh, rlogin, rexec";
        type empty;
      }
      leaf rip {
        tailf:info
          "Routing Information Protocol";
        type empty;
      }
      leaf rsrb {
        tailf:info
          "Remote Source-Route Bridging";
        type empty;
      }
      leaf rsvp {
        tailf:info
          "Resource Reservation Protocol";
        type empty;
      }
      leaf rtcp {
        tailf:info
          "Real Time Control Protocol";
        type empty;
      }
      container rtp {
        tailf:info
          "Real Time Protocol";
        presence "enable rtp matching";
        leaf audio {
          tailf:info
            "Match voice packets";
          type empty;
        }
        leaf payload-type {
          tailf:info
            "Match an explicit PT";
          type string {
            tailf:info
              "WORD;;Enter a string as the sub-protocol parameter";
          }
        }
        leaf video {
          tailf:info
            "Match video packets";
          type empty;
        }
      }
      leaf rtsp {
        tailf:info
          "Real Time Streaming Protocol";
        type empty;
      }
      leaf secure-ftp {
        tailf:info
          "FTP over TLS/SSL";
        type empty;
      }
      leaf secure-http {
        tailf:info
          "Secured HTTP";
        type empty;
      }
      leaf secure-imap {
        tailf:info
          "Internet Message Access Protocol over TLS/SSL";
        type empty;
      }
      leaf secure-irc {
        tailf:info
          "Internet Relay Chat over TLS/SSL";
        type empty;
      }
      leaf secure-ldap {
        tailf:info
          "Lightweight Directory Access Protocol over TLS/SSL";
        type empty;
      }
      leaf secure-nntp {
        tailf:info
          "Network News Transfer Protocol over TLS/SSL";
        type empty;
      }
      leaf secure-pop3 {
        tailf:info
          "Post Office Protocol over TLS/SSL";
        type empty;
      }
      leaf secure-telnet {
        tailf:info
          "Telnet over TLS/SSL";
        type empty;
      }
      leaf sip {
        tailf:info
          "Session Initiation Protocol";
        type empty;
      }
      leaf skinny {
        tailf:info
          "Skinny Protocol";
        type empty;
      }
      leaf smtp {
        tailf:info
          "Simple Mail Transfer Protocol";
        type empty;
      }
      leaf snapshot {
        tailf:info
          "Snapshot routing support";
        type empty;
      }
      leaf snmp {
        tailf:info
          "Simple Network Management Protocol";
        type empty;
      }
      leaf socks {
        tailf:info
          "SOCKS";
        type empty;
      }
      leaf sqlnet {
        tailf:info
          "SQL*NET for Oracle";
        type empty;
      }
      leaf sqlserver {
        tailf:info
          "MS SQL Server";
        type empty;
      }
      leaf ssh {
        tailf:info
          "Secured Shell";
        type empty;
      }
      leaf streamwork {
        tailf:info
          "Xing Technology StreamWorks player";
        type empty;
      }
      leaf stun {
        tailf:info
          "Serial Tunnel";
        type empty;
      }
      leaf sunrpc {
        tailf:info
          "Sun RPC";
        type empty;
      }
      leaf syslog {
        tailf:info
          "System Logging Utility";
        type empty;
      }
      leaf telnet {
        tailf:info
          "Telnet";
        type empty;
      }
      leaf tftp {
        tailf:info
          "Trivial File Transfer Protocol";
        type empty;
      }
      leaf vdolive {
        tailf:info
          "VDOLive streaming video";
        type empty;
      }
      leaf vofr {
        tailf:info
          "voice over Frame Relay packets";
        type empty;
      }
      leaf winmx {
        tailf:info
          "WinMx file-sharing application";
        type empty;
      }
      leaf xwindows {
        tailf:info
          "X-Windows remote access";
        type empty;
      }
    }
    leaf-list qos-group {
      tailf:info
        "Qos-group";
      tailf:cli-list-syntax;
      type uint16 {
        tailf:info
          "<0-99>;;Qos Group value";
        range "0..99";
      }
    }
    container source-address {
      tailf:info
        "Source address";
      leaf-list mac {
        tailf:info
          "MAC address";
        tailf:cli-list-syntax;
        type string {
          tailf:info
            "H.H.H;;MAC address";
        }
      }
    }
    leaf-list vlan {
      tailf:info
        "VLANs to match";
      tailf:cli-flat-list-syntax;
      type uint16 {
        tailf:info
          "<1-4094>;;VLAN id";
        range "1..4094";
      }
    }
  }

  grouping ncs_rpc_notif_ntp-server-grouping {
    list server-list {
      tailf:cli-drop-node-name;
      tailf:cli-suppress-mode;
      tailf:cli-delete-when-empty;
      tailf:cli-compact-syntax;
      tailf:cli-reset-container;
      key "ip-address";
      leaf ip-address {
        tailf:cli-disallow-value "vrf";
        type ncs_rpc_notif_host-type;
      }
      leaf key {
        tailf:info
          "Configure peer authentication key";
        type uint32 {
          tailf:info
            "<0-4294967295>;;Peer key number";
        }
      }
      leaf prefer {
        tailf:info
          "Prefer this peer when possible";
        type empty;
      }
      leaf version {
        tailf:info
          "    Configure NTP version";
        type uint8 {
          tailf:info
            "<1-3>;;NTP version number";
        }
      }
    }
  }

  grouping ncs_rpc_notif_line-grouping {
    container access-class {
      tailf:info
        "Filter connections based on an IP access list";
      tailf:cli-compact-syntax;
      tailf:cli-sequence-commands;
      tailf:cli-reset-container;
      tailf:cli-flatten-container;
      list acccess-list {
        tailf:cli-drop-node-name;
        tailf:cli-compact-syntax;
        tailf:cli-reset-container;
        tailf:cli-suppress-mode;
        tailf:cli-delete-when-empty;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type ncs_rpc_notif_exp-acl-type;
          mandatory true;
        }
        leaf vrf-also {
          tailf:info
            "Same access list is applied for all VRFs";
          type empty;
        }
      }
    }
    leaf escape-character {
      tailf:info
        "Change the current line's escape character";
      type union {
        type uint8 {
          tailf:info
            "ASCII decimal equivalent";
        }
        type enumeration {
          enum "BREAK" {
            tailf:info
              "Cause escape on BREAK";
          }
          enum "DEFAULT" {
            tailf:info
              "Use default escape character";
          }
          enum "NONE" {
            tailf:info
              "Disable escape entirely";
          }
        }
      }
    }
    leaf exec {
      tailf:info
        "Configure EXEC";
      tailf:cli-boolean-no;
      tailf:cli-trim-default;
      type boolean;
      default "true";
    }
    container exec-timeout {
      tailf:info
        "Set the EXEC timeout";
      tailf:cli-sequence-commands;
      tailf:cli-compact-syntax;
      leaf minutes {
        tailf:info
          "<0-35791>;;Timeout in minutes";
        tailf:cli-drop-node-name;
        type uint32;
      }
      leaf seconds {
        tailf:info
          "<0-2147483>;;Timeout in seconds";
        tailf:cli-drop-node-name;
        type uint32;
      }
    }
    container logging {
      tailf:info
        "Modify message logging facilities";
      container synchronous {
        tailf:info
          "Synchronized message output";
        presence "true";
      }
    }
    container login {
      tailf:info
        "Enable password checking";
      tailf:cli-delete-when-empty;
      presence "true";
      leaf local {
        type empty;
      }
      leaf authentication {
        type string;
      }
    }
    container password {
      tailf:info
        "Set a password";
      tailf:cli-compact-syntax;
      tailf:cli-sequence-commands;
      uses ncs_rpc_notif_password-07-grouping;
    }
    container privilege {
      tailf:info
        "Change privilege level for line";
      leaf level {
        tailf:info
          "Assign default privilege level for line";
        type uint8 {
          tailf:info
            "<0-15>;;Default privilege level for line";
          range "0..15";
        }
      }
    }
    container session-timeout {
      tailf:info
        "Set interval for closing connection when there is no input traffic";
      tailf:cli-sequence-commands;
      tailf:cli-compact-syntax;
      leaf session-timeout-value {
        tailf:cli-drop-node-name;
        type uint16 {
          tailf:info
            "<0-35791>;;Session timeout interval in minutes";
          range "0..35791";
        }
      }
      leaf output {
        tailf:info
          "Include output traffic as well as input traffic";
        type empty;
      }
    }
    leaf stopbits {
      tailf:info
        "Set async line stop bits";
      type enumeration {
        enum "1" {
          tailf:info
            "One stop bit";
        }
        enum "1.5" {
          tailf:info
            "One and one-half stop bits";
        }
        enum "2" {
          tailf:info
            "Two stop bits";
        }
      }
    }
    container telnet {
      tailf:info
        "Telnet protocol-specific configuration";
      leaf transparent {
        tailf:info
          "Send a CR as a CR followed by a NULL instead of a CR followed by a LF";
        type empty;
      }
    }
    container transport {
      tailf:info
        "Define transport protocols for line";
      tailf:cli-incomplete-no;
      leaf-list input {
        tailf:info
          "Define which protocols to use when connecting to the terminal server";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat";
          enum "pad" {
            tailf:info
              "X.3 PAD";
          }
          enum "udptn" {
            tailf:info
              "UDPTN async via UDP protocol";
          }
          enum "rlogin" {
            tailf:info
              "Unix rlogin protocol";
          }
        }
      }
      leaf-list output {
        tailf:info
          "Define which protocols to use for outgoing connections";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
        }
      }
      leaf preferred {
        tailf:info
          "Specify the preferred protocol to use";
        tailf:cli-no-value-on-delete;
        type enumeration {
          enum "none" {
            tailf:info
              "No protocols";
          }
          enum "ssh" {
            tailf:info
              "TCP/IP SSH protocol";
          }
          enum "telnet" {
            tailf:info
              "TCP/IP Telnet protocol";
          }
        }
      }
    }
  }

  grouping ncs_rpc_notif_queue-size-grouping {
    leaf queue-size-1 {
      tailf:cli-drop-node-name;
      type uint8 {
        tailf:info
          "<1-100>;;enter percent of queue size between 1 and 100";
        range "1..100";
      }
    }
    leaf queue-size-2 {
      tailf:cli-drop-node-name;
      type uint8 {
        tailf:info
          "<1-100>;;enter percent of queue size between 1 and 100";
        range "1..100";
      }
    }
    leaf queue-size-3 {
      tailf:cli-drop-node-name;
      type uint8 {
        tailf:info
          "<1-100>;;enter percent of queue size between 1 and 100";
        range "1..100";
      }
    }
    leaf queue-size-4 {
      tailf:cli-drop-node-name;
      type uint8 {
        tailf:info
          "<1-100>;;enter percent of queue size between 1 and 100";
        range "1..100";
      }
    }
    leaf queue-size-5 {
      tailf:cli-drop-node-name;
      type uint8 {
        tailf:info
          "<1-100>;;enter percent of queue size between 1 and 100";
        range "1..100";
      }
    }
    leaf queue-size-6 {
      tailf:cli-drop-node-name;
      type uint8 {
        tailf:info
          "<1-100>;;enter percent of queue size between 1 and 100";
        range "1..100";
      }
    }
    leaf queue-size-7 {
      tailf:cli-drop-node-name;
      type uint8 {
        tailf:info
          "<1-100>;;enter percent of queue size between 1 and 100";
        range "1..100";
      }
    }
    leaf queue-size-8 {
      tailf:cli-drop-node-name;
      type uint8 {
        tailf:info
          "<1-100>;;enter percent of queue size between 1 and 100";
        range "1..100";
      }
    }
  }

  grouping ncs_rpc_notif_interface-common-grouping {
    leaf description {
      tailf:info
        "Interface specific description";
      tailf:cli-multi-value;
      tailf:cli-full-command;
      type string {
        length "0..240";
      }
    }
    container authentication {
      tailf:info
        "set the port-control value";
      leaf port-control {
        type enumeration {
          enum "auto" {
            tailf:info
              "PortState will be set to AUTO";
          }
          enum "force-authorized" {
            tailf:info
              "PortState set to Authorized";
          }
          enum "force-unauthorized" {
            tailf:info
              "PortState will be set to UnAuthorized";
          }
        }
      }
    }
    container mab {
      presence "true";
      leaf eap {
        type empty;
      }
    }
    container l2protocol-tunnel {
      tailf:info
        "Tunnel Layer2 protocols";
      tailf:cli-delete-when-empty;
      presence "true";
      leaf cdp {
        tailf:info
          "Cisco Discovery Protocol";
        type empty;
      }
      container drop-threshold {
        tailf:info
          "Set drop threshold for protocol packets";
        leaf packet-rate {
          tailf:cli-drop-node-name;
          type uint16 {
            tailf:info
              "<1-4096>;;Packets/sec rate beyond which protocol packets will be dropped";
            range "1..4096";
          }
        }
        leaf cdp {
          tailf:info
            "Cisco Discovery Protocol";
          type uint16 {
            tailf:info
              "<1-4096>;;Packets/sec rate beyond which protocol packets will be dropped";
            range "1..4096";
          }
        }
        leaf stp {
          tailf:info
            "Spanning Tree Protocol";
          type uint16 {
            tailf:info
              "<1-4096>;;Packets/sec rate beyond which protocol packets will be dropped";
            range "1..4096";
          }
        }
        leaf vtp {
          tailf:info
            "Vlan Trunking Protocol";
          type uint16 {
            tailf:info
              "<1-4096>;;Packets/sec rate beyond which protocol packets will be dropped";
            range "1..4096";
          }
        }
      }
      container shutdown-threshold {
        tailf:info
          "Set shutdown threshold for protocol packets";
        leaf packet-rate {
          tailf:cli-drop-node-name;
          type uint16 {
            tailf:info
              "<1-4096>;;Packets/sec rate beyond which interface is put to err-disable";
            range "1..4096";
          }
        }
        leaf cdp {
          tailf:info
            "Cisco Discovery Protocol";
          type uint16 {
            tailf:info
              "<1-4096>;;Packets/sec rate beyond which interface is put to err-disable";
            range "1..4096";
          }
        }
        leaf stp {
          tailf:info
            "Spanning Tree Protocol";
          type uint16 {
            tailf:info
              "<1-4096>;;Packets/sec rate beyond which interface is put to err-disable";
            range "1..4096";
          }
        }
        leaf vtp {
          tailf:info
            "Vlan Trunking Protocol";
          type uint16 {
            tailf:info
              "<1-4096>;;Packets/sec rate beyond which interface is put to err-disable";
            range "1..4096";
          }
        }
      }
      leaf stp {
        tailf:info
          "Spanning Tree Protocol";
        type empty;
      }
      leaf vtp {
        tailf:info
          "Vlan Trunking Protocol";
        type empty;
      }
    }
    container encapsulation {
      tailf:info
        "Set encapsulation type for an interface";
      container dot1Q {
        tailf:info
          "IEEE 802.1Q Virtual LAN";
        tailf:cli-sequence-commands;
        tailf:cli-compact-syntax;
        leaf vlan-id {
          tailf:cli-drop-node-name;
          type uint16 {
            tailf:info
              "<1-4094>;;IEEE 802.1Q VLAN ID required";
            range "1..4094";
          }
        }
        leaf native {
          tailf:info
            "Make this as native vlan";
          type empty;
        }
      }
      container isl {
        tailf:info
          "Inter Switch Link - Virtual LAN encapsulation";
        tailf:cli-sequence-commands;
        tailf:cli-compact-syntax;
        leaf vlan-id {
          tailf:cli-drop-node-name;
          type uint16 {
            tailf:info
              "<1-4095>;;Virtual LAN Identifier.";
            range "1..4095";
          }
        }
      }
      container ppp {
        tailf:info
          "Point-to-Point protocol";
        presence "true";
      }
      container slip {
        tailf:info
          "Serial Line IP";
        presence "true";
      }
      container frame-relay {
        tailf:info
          "Frame Relay networks";
        tailf:cli-delete-when-empty;
        presence "true";
        leaf ietf {
          tailf:info
            "Use RFC1490/RFC2427 encapsulation";
          type empty;
        }
      }
    }
    container fair-queue-conf {
      tailf:cli-no-keyword;
      tailf:cli-drop-node-name;
      when "not(../name[contains(.,'.')])" {
        tailf:xpath-root 3;
        tailf:dependency "../name";
      }
      leaf fair-queue {
        tailf:cli-boolean-no;
        tailf:cli-trim-default;
        type boolean;
        default "true";
      }
    }
    container fair-queue {
      tailf:info
        "Enable Fair Queuing on an Interface";
      tailf:cli-incomplete-no;
      leaf incomplete {
        type empty;
      }
    }
    container flowcontrol {
      tailf:info
        "Configure flow operation.";
      leaf receive {
        tailf:info
          "Configure receiving flow operation";
        type enumeration {
          enum "desired" {
            tailf:info
              "Allow but do not require flow-control packets on port";
          }
          enum "off" {
            tailf:info
              "Disable flow-control packets on port";
          }
          enum "on" {
            tailf:info
              "Enable flow-control packets on port";
          }
        }
      }
      leaf send {
        tailf:info
          "Configure sending flow operation";
        type enumeration {
          enum "desired" {
            tailf:info
              "Allow but do not require flow-control packets on port";
          }
          enum "off" {
            tailf:info
              "Disable flow-control packets on port";
          }
          enum "on" {
            tailf:info
              "Enable flow-control packets on port";
          }
        }
      }
    }
    choice keepalive-choice {
      leaf keepalive {
        tailf:info
          "Enable keepalive";
        tailf:cli-boolean-no;
        type boolean;
      }
      container keepalive-settings {
        tailf:cli-drop-node-name;
        container keepalive {
          tailf:info
            "Enable keepalive";
          leaf period {
            tailf:cli-drop-node-name;
            type uint16 {
              tailf:info
                "<0-32767>;;Keepalive period (default 10 seconds)";
              range "0..32767";
            }
          }
        }
      }
    }
    container snmp {
      tailf:info
        "Modify SNMP interface parameters";
      container ifindex {
        tailf:info
          "Persist ifindex for the interface";
        choice ifindex-choice {
          leaf persist {
            tailf:info
              "Enable/Disable ifIndex persistence ";
            type empty;
          }
          leaf clear {
            tailf:info
              "Clear Enable/Disable ifIndex persistence";
            tailf:cli-trim-default;
            tailf:cli-boolean-no;
            type boolean;
            default "true";
          }
        }
      }
      container trap {
        tailf:info
          "Allow a specific SNMP trap";
        leaf link-status {
          tailf:info
            "Allow SNMP LINKUP and LINKDOWN traps";
          tailf:cli-boolean-no;
          tailf:cli-trim-default;
          tailf:cli-full-command;
          type boolean;
          default "true";
        }
        container link-status-capas {
          tailf:cli-drop-node-name;
          container link-status {
            tailf:info
              "Allow SNMP LINKUP and LINKDOWN traps";
            container permit {
              tailf:info
                "Permit the following capability";
              leaf duplicates {
                tailf:info
                  "Permit duplicate SNMP LINKUP and LINKDOWN traps";
                type empty;
              }
            }
          }
        }
      }
    }
    container bfd {
      tailf:info
        "BFD interface configuration commands";
      leaf echo {
        tailf:info
          "Use echo adjunct as bfd detection mechanism";
        type empty;
      }
      container interval {
        tailf:info
          "Transmit interval between BFD packets";
        tailf:cli-reset-container;
        tailf:cli-compact-syntax;
        tailf:cli-sequence-commands;
        leaf msecs {
          tailf:cli-drop-node-name;
          tailf:cli-incomplete-command;
          type uint16 {
            tailf:info
              "<100-999>;;Milliseconds";
            range "100..999";
          }
        }
        leaf min_rx {
          tailf:info
            "Minimum receive interval capability";
          tailf:cli-incomplete-command;
          type uint16 {
            tailf:info
              "<100-999>;;Milliseconds";
            range "100..999";
          }
        }
        leaf multiplier {
          tailf:info
            "Multiplier value used to compute holddown";
          type uint8 {
            tailf:info
              "<3-50>;;value used to multiply the interval";
            range "3..50";
          }
        }
      }
    }
    container bandwidth {
      tailf:info
        "Set bandwidth informational parameter";
      tailf:cli-sequence-commands {
        tailf:cli-reset-siblings;
      }
      tailf:cli-compact-syntax;
      leaf inherit {
        tailf:cli-optional-in-sequence;
        tailf:info
          "Specify how bandwidth is inherited";
        type empty;
      }
      leaf kilobits {
        tailf:cli-drop-node-name;
        type uint32 {
          tailf:info
            "<1-10000000>;;Bandwidth in kilobits";
          range "1..10000000";
        }
      }
    }
    container cdp {
      tailf:info
        "CDP interface subcommands";
      leaf enable {
        tailf:info
          "Enable CDP on interface";
        tailf:cli-boolean-no;
        tailf:cli-trim-default;
        tailf:cli-full-command;
        type boolean;
        default "true";
      }
      container tlv {
        tailf:info
          "Enable exchange of specific tlv information";
        container app {
          tailf:info
            "Enable/Configure Application TLV";
          tailf:cli-display-separated;
          tailf:cli-compact-syntax;
          tailf:cli-reset-container;
          tailf:cli-sequence-commands;
          presence "true";
          leaf tlvtype {
            tailf:info
              "Configure APP TLV";
            tailf:cli-incomplete-command;
            type uint16 {
              tailf:info
                "Configure App TLV Type information";
              range "1001..65535";
            }
          }
          leaf value {
            tailf:info
              "Configure App TLV Value information";
            type string {
              tailf:info
                "WORD;;Configure App TLV value information";
            }
          }
        }
        leaf server-location {
          tailf:info
            "Enable CDP location server on interface";
          tailf:cli-full-command;
          type empty;
        }
        leaf location {
          tailf:info
            "Exchange location information";
          tailf:cli-full-command;
          type empty;
        }
      }
    }
    container dampening {
      tailf:info
        "Enable event dampening";
      presence "true";
      leaf dampening-time {
        tailf:cli-drop-node-name;
        tailf:cli-delete-container-on-delete;
        tailf:info
          "<1-30>;;Half-life time for penalty";
        type uint16 {
          range "1..30";
        }
      }
    }
    container hold-queue {
      tailf:info
        "Set hold queue depth";
      tailf:cli-compact-syntax;
      tailf:cli-reset-container;
      tailf:cli-sequence-commands;
      leaf queue-length {
        tailf:cli-drop-node-name;
        type uint16 {
          tailf:info
            "<0-4096>;;Queue length";
          range "0..4096";
        }
      }
      leaf direction {
        tailf:cli-drop-node-name;
        type enumeration {
          enum "in" {
            tailf:info
              "Input queue";
          }
          enum "out" {
            tailf:info
              "Output queue";
          }
        }
      }
    }
    container mpls {
      tailf:info
        "Configure MPLS interface parameters";
      container accounting {
        tailf:info
          "Enable MPLS accounting on this interface";
        container experimental {
          tailf:info
            "Count packets by MPLS experimental value on this interface";
          leaf input {
            tailf:info
              "received packets";
            type empty;
          }
          leaf output {
            tailf:info
              "transmitted packets";
            type empty;
          }
        }
      }
      container bgp {
        tailf:info
          "MPLS BGP";
        leaf forwarding {
          tailf:info
            "Configure MPLS forwarding for directly connected BGP peers";
          type empty;
        }
      }
      leaf ip {
        tailf:info
          "Configure dynamic MPLS forwarding for IP";
        tailf:cli-full-command;
        type empty;
      }
      container label {
        tailf:info
          "Label properties";
        leaf protocol {
          tailf:info
            "Configure label/tag distribution protocol (LDP/TDP)";
          type enumeration {
            enum "both" {
              tailf:info
                "Use LDP or TDP (Adapt to peer on multiaccess interface)";
            }
            enum "ldp" {
              tailf:code-name "lab_ldp";
              tailf:info
                "Use LDP (default)";
            }
            enum "tdp" {
              tailf:code-name "lab_tdp";
              tailf:info
                "Use TDP";
            }
          }
        }
      }
      container ldp {
        tailf:info
          "Configure Label Distribution Protocol (LDP) parameters";
        container discovery {
          tailf:info
            "Configure interface LDP Discovery parameters";
          leaf transport-address {
            tailf:info
              "Specify interface LDP transport address";
            type ncs_rpc_notif_ldp-discovery-address-type;
          }
        }
      }
      leaf mtu {
        tailf:info
          "Set MPLS Maximum Transmission Unit";
        tailf:cli-full-command;
        type union {
          type uint16 {
            range "1501..1524";
            tailf:info
              "<1501-1524>;;MTU (baby giants bytes)";
          }
          type uint16 {
            range "64..1500";
            tailf:info
              "<64-1500>;;MTU (bytes)";
          }
          type uint16 {
            tailf:info
              "<64-9216>;;MTU size in bytes";
            range "64..9216";
          }
        }
      }
      container traffic-eng {
        tailf:info
          "Configure Traffic Engineering parameters";
        leaf administrative-weight {
          tailf:info
            "Set the administrative weight for the interface";
          tailf:cli-full-command;
          type uint32 {
            range "0..4294967295";
            tailf:info
              "<0-4294967295>;;Weight";
          }
        }
        leaf attribute-flags {
          tailf:info
            "Set user-defined interface attibute flags";
          tailf:cli-full-command;
          type string {
            tailf:info
              "<0x0-0xFFFFFFFF>;;Attribute flags";
          }
        }
        container flooding {
          tailf:info
            "Set flooding parameters";
          container thresholds {
            tailf:info
              "Set flooding thresholds";
            leaf-list down {
              tailf:info
                "Set the thresholds for decreased resource availability";
              tailf:cli-flat-list-syntax;
              type uint8 {
                range "0..100";
                tailf:info
                  "<0-100>;;decreased bandwidth usage (percent)";
              }
            }
            leaf-list up {
              tailf:info
                "Set the thresholds for increased resource availability";
              tailf:cli-flat-list-syntax;
              type uint8 {
                range "0..100";
                tailf:info
                  "<0-100>;;increased bandwidth usage (percent)";
              }
            }
          }
        }
        leaf tunnels {
          tailf:info
            "enable MPLS Traffic Engineering tunnels";
          tailf:cli-full-command;
          type empty;
        }
      }
    }
    choice vrf-choice {
      container ip-vrf {
        tailf:cli-no-keyword;
        tailf:cli-drop-node-name;
        container ip {
          container vrf {
            leaf forwarding {
              tailf:info
                "Configure forwarding table";
              type string {
                tailf:info
                  "WORD;;VRF name";
              }
              // NCS drop tailf-common:non-strict-leafref statement
            }
          }
        }
      }
      container vrf {
        tailf:info
          "VPN Routing/Forwarding parameters on the interface";
        leaf forwarding {
          tailf:info
            "Configure forwarding table";
          type string {
            tailf:info
              "WORD;;VRF name";
          }
          // NCS drop tailf-common:non-strict-leafref statement
        }
      }
    }
    container ip {
      tailf:info
        "Interface Internet Protocol config commands";
      container access-group {
        tailf:info
          "Specify access control for packets";
        tailf:cli-sequence-commands;
        tailf:cli-compact-syntax;
        leaf access-list {
          tailf:cli-drop-node-name;
          tailf:cli-incomplete-command;
          type ncs_rpc_notif_exp-acl-type;
        }
        leaf direction {
          tailf:cli-drop-node-name;
          tailf:cli-full-command;
          type enumeration {
            enum "in" {
              tailf:code-name "access_group_direction_in";
              tailf:info
                "inbound packets";
            }
            enum "out" {
              tailf:code-name "access_group_direction_out";
              tailf:info
                "outbound packets";
            }
          }
        }
      }
      container vrf {
        tailf:info
          "VPN Routing/Forwarding parameters on the interface";
        leaf receive {
          tailf:info
            "Add Interface Address into VRF Table";
          tailf:cli-full-command;
          type string {
            tailf:info
              "WORD;;Table name";
          }
        }
        leaf sitemap {
          tailf:info
            "Configure route-map for routesreceived from this site";
          tailf:cli-full-command;
          type string {
            tailf:info
              "WORD;;Name of the route-map";
          }
        }
      }
      choice address-choice {
        leaf unnumbered {
          tailf:info
            "Enable IP processing without an explicit address";
          type string;
        }
        container no-address {
          tailf:cli-drop-node-name;
          leaf address {
            tailf:cli-boolean-no;
            tailf:cli-trim-default;
            type boolean;
            default "true";
          }
        }
        container address {
          tailf:info
            "Set the IP address of an interface";
          tailf:cli-incomplete-command;
          tailf:cli-incomplete-no;
          choice address-choice {
            case fixed-case {
              container primary {
                tailf:cli-drop-node-name;
                tailf:cli-sequence-commands;
                tailf:cli-compact-syntax;
                tailf:cli-incomplete-command;
                tailf:cli-incomplete-no;
                leaf address {
                  tailf:cli-incomplete-command;
                  tailf:cli-drop-node-name;
                  tailf:cli-incomplete-no;
                  tailf:cli-diff-dependency "/ios:vrf/definition/address-family/ipv4" {
                    tailf:xpath-root 3;
                  }
                  tailf:cli-diff-dependency "../../../../vrf/forwarding" {
                    tailf:xpath-root 3;
                  }
                  mandatory true;
                  type inet:ipv4-address {
                    tailf:info
                      "A.B.C.D;;IP address";
                  }
                }
                leaf mask {
                  tailf:cli-drop-node-name;
                  mandatory true;
                  type inet:ipv4-address {
                    tailf:info
                      "A.B.C.D;;IP subnet mask";
                  }
                }
              }
              list secondary {
                key "address";
                tailf:cli-incomplete-command;
                tailf:cli-sequence-commands;
                tailf:cli-compact-syntax;
                tailf:cli-drop-node-name;
                tailf:cli-suppress-mode;
                tailf:cli-incomplete-no;
                leaf address {
                  tailf:cli-incomplete-no;
                  type inet:ipv4-address {
                    tailf:info
                      "A.B.C.D;;IP address";
                  }
                }
                leaf mask {
                  tailf:cli-drop-node-name;
                  tailf:cli-incomplete-command;
                  mandatory true;
                  type inet:ipv4-address {
                    tailf:info
                      "A.B.C.D;;IP subnet mask";
                  }
                }
                leaf secondary {
                  tailf:info
                    "Make this IP address a secondary address";
                  type empty;
                }
              }
            }
            case dhcp-case {
              container dhcp {
                tailf:info
                  "IP Address negotiated via DHCP";
                presence "IP Address negotiated via DHCP";
                tailf:cli-sequence-commands;
                container client-id {
                  tailf:info
                    "Specify client-id to use";
                  tailf:cli-flatten-container;
                  tailf:cli-optional-in-sequence;
                  tailf:cli-diff-dependency "/ios:interface" {
                    tailf:xpath-root 3;
                  }
                  uses ncs_rpc_notif_ethernet-grouping;
                }
                leaf hostname {
                  tailf:info
                    "Specify value for hostname option";
                  type string {
                    tailf:info
                      "WORD;;hostname string";
                  }
                }
              }
            }
          }
        }
      }
      container flow {
        tailf:info
          "NetFlow related commands";
        leaf ingress {
          tailf:info
            "Enable inbound NetFlow";
          type empty;
        }
        leaf egress {
          tailf:info
            "Enable outbound NetFlow";
          type empty;
        }
      }
      container helper-address {
        tailf:info
          "Specify a destination address for UDP broadcasts";
        tailf:cli-compact-syntax;
        tailf:cli-sequence-commands {
          tailf:cli-reset-siblings;
        }
        choice helper-choice {
          leaf global {
            tailf:info
              "Helper-address is global";
            tailf:cli-optional-in-sequence;
            type empty;
          }
          leaf vrf {
            tailf:info
              "VRF name for helper-address (if different from interface VRF)";
            tailf:cli-optional-in-sequence;
            tailf:cli-diff-dependency "/ios:ip/vrf" {
              tailf:xpath-root 3;
            }
            tailf:cli-diff-dependency "/ios:vrf/definition" {
              tailf:xpath-root 3;
            }
            type string {
              tailf:info
                "WORD;;VPN Routing/Forwarding instance name";
            }
          }
        }
        leaf address {
          tailf:cli-drop-node-name;
          type inet:ipv4-address {
            tailf:info
              "A.B.C.D;;IP destination address";
          }
        }
      }
      container ospf {
        tailf:info
          "OSPF interface commands";
        list process-id {
          tailf:cli-drop-node-name;
          tailf:cli-suppress-mode;
          tailf:cli-delete-when-empty;
          tailf:cli-compact-syntax;
          tailf:cli-incomplete-command;
          tailf:cli-reset-container;
          tailf:cli-sequence-commands;
          key "id";
          leaf id {
            type uint16 {
              tailf:info
                "<1-65535>;;Process ID";
            }
          }
          leaf area {
            type union {
              type uint32 {
                tailf:info
                  "<0-4294967295>;;OSPF area ID as a decimal value";
              }
              type inet:ipv4-address {
                tailf:info
                  "A.B.C.D;;OSPF area ID in IP address format";
              }
            }
          }
          leaf secondaries {
            tailf:info
              "Include or exclude secondary IP addresses";
            type empty;
          }
          leaf none {
            tailf:info
              "Do not include secondary IP addresses";
            type empty;
          }
        }
        leaf network {
          tailf:info
            "Network type";
          type enumeration {
            enum "broadcast" {
              tailf:info
                "Specify OSPF broadcast multi-access network";
            }
            enum "non-broadcast" {
              tailf:info
                "Specify OSPF NBMA network";
            }
            enum "point-to-multipoint" {
              tailf:info
                "Specify OSPF point-to-multipoint network";
            }
            enum "point-to-point" {
              tailf:info
                "Specify OSPF point-to-point network";
            }
          }
        }
        container bfd {
          tailf:info
            "BFD interface configuration commands";
          presence "true";
          leaf enable {
            tailf:cli-full-command;
            tailf:cli-drop-node-name;
            type enumeration {
              enum "disable" {
                tailf:info
                  "Disable BFD for this interface";
              }
            }
          }
        }
        leaf cost {
          tailf:info
            "Interface cost";
          type uint16 {
            tailf:info
              "<1-65535>;;Cost";
            range "1..65535";
          }
        }
      }
      container pim {
        tailf:info
          "PIM interface commands";
        leaf sparse-mode {
          tailf:info
            "Enable PIM sparse-mode operation";
          type empty;
        }
        leaf dr-priority {
          tailf:info
            "PIM router DR priority";
          type uint32 {
            tailf:info
              "<0-4294967294>;;DR priority, preference given to larger value";
          }
        }
      }
      container policy {
        tailf:info
          "Enable policy routing";
        leaf route-map {
          tailf:info
            "Policy route-map";
          type string {
            tailf:info
              "WORD;;Route map name";
          }
        }
      }
      leaf proxy-arp {
        tailf:info
          "Enable proxy ARP";
        tailf:cli-boolean-no;
        tailf:cli-trim-default;
        type boolean;
        default "true";
      }
      container route-cache-conf {
        tailf:cli-no-keyword;
        tailf:cli-drop-node-name;
        leaf route-cache {
          tailf:cli-boolean-no;
          tailf:cli-trim-default;
          type boolean;
          default "true";
        }
      }
      container route-cache {
        tailf:info
          "Enable fast-switching cache for outgoing packets";
        tailf:cli-incomplete-no;
        leaf cef {
          tailf:info
            "Enable Cisco Express Forwarding";
          tailf:cli-boolean-no;
          tailf:cli-trim-default;
          type boolean;
          default "true";
        }
        leaf flow {
          tailf:info
            "Enable Flow fast-switching cache";
          tailf:cli-boolean-no;
          tailf:cli-trim-default;
          type boolean;
          default "false";
        }
        leaf policy {
          tailf:info
            "Enable fast-switching policy cache for outgoing packets";
          tailf:cli-boolean-no;
          tailf:cli-trim-default;
          type boolean;
          default "false";
        }
        leaf same-interface {
          tailf:info
            "Enable fast-switching on the same interface";
          tailf:cli-boolean-no;
          tailf:cli-trim-default;
          type boolean;
          default "false";
        }
      }
      container igmp {
        tailf:info
          "IGMP interface commands";
        container static-group {
          tailf:info
            "IGMP static multicast group";
          list groups {
            tailf:cli-suppress-mode;
            tailf:cli-delete-when-empty;
            tailf:cli-drop-node-name;
            key "name";
            leaf name {
              tailf:cli-suppress-range;
              type union {
                type inet:ipv4-address {
                  tailf:info
                    "A.B.C.D;;IP group address";
                }
                type enumeration {
                  enum "*" {
                    tailf:info
                      "Populated for all groups";
                  }
                }
              }
            }
          }
          list class-map {
            tailf:info
              "Class map of type multicast-flows";
            key "id";
            leaf id {
              type string;
            }
          }
        }
      }
      leaf redirects {
        tailf:info
          "Enable sending ICMP Redirect messages";
        type empty;
      }
      container tcp {
        tailf:info
          "TCP header compression and other parameters";
        leaf adjust-mss {
          tailf:info
            "Adjust the mss of transit packets";
          type uint16 {
            tailf:info
              "<500-1460>;;Maximum segment size in bytes";
            range "500..1460";
          }
        }
      }
      container virtual-reassembly {
        tailf:cli-compact-syntax;
        leaf max-reassemblies {
          type uint32;
        }
        leaf max-fragments {
          type uint32;
        }
        leaf timeout {
          type uint32;
        }
        leaf drop-fragments {
          type empty;
        }
        leaf in {
          type empty;
        }
      }
      container dhcp {
        tailf:info
          "Configure DHCP parameters for this interface";
        container relay {
          tailf:info
            "DHCP relay configuration parameters";
          container information {
            tailf:info
              "DHCP relay information option";
            container check-reply {
              tailf:info
                "Validate relay information in BOOTREPLY";
              presence "true";
              leaf none {
                tailf:info
                  "Set to none";
                type empty;
              }
            }
            container option {
              tailf:info
                "DHCP relay information option";
              leaf subscriber-id {
                tailf:info
                  "Subscriber identifier sub option";
                type string {
                  tailf:info
                    "WORD;;Subscriber identifier string";
                }
              }
            }
            container option-insert {
              tailf:info
                "Insert relay information in BOOTREQUEST";
              presence "true";
              leaf none {
                tailf:info
                  "Set to none";
                type empty;
              }
            }
            leaf policy-action {
              tailf:info
                "Define reforwarding policy";
              type enumeration {
                enum "drop" {
                  tailf:info
                    "Do not forward BOOTREQUEST message";
                }
                enum "encapsulate" {
                  tailf:info
                    "Encapsulate existing information";
                }
                enum "keep" {
                  tailf:info
                    "Leave existing information alone";
                }
                enum "replace" {
                  tailf:info
                    "Replace existing information";
                }
              }
            }
            leaf trusted {
              tailf:info
                "Received DHCP packet may contain relay info option with zero giaddr";
              type empty;
            }
          }
        }
        container snooping {
          tailf:info
            "DHCP Snooping";
          container limit {
            tailf:info
              "DHCP Snooping limit";
            leaf rate {
              tailf:info
                "DHCP Snooping limit";
              type uint16 {
                tailf:info
                  "<1-2048>;;DHCP snooping rate limit";
                range "1..2048";
              }
            }
          }
          leaf trust {
            tailf:info
              "DHCP Snooping trust config";
            type empty;
          }
          list vlan {
            tailf:info
              "DHCP Snooping vlan";
            key "id";
            max-elements 1;
            leaf id {
              tailf:cli-drop-node-name;
              type uint16 {
                tailf:info
                  "<1-4094>;;DHCP Snooping vlan";
                range "1..4094";
              }
            }
            container information {
              tailf:info
                "DHCP Snooping information";
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id (3-63 chars)";
                        length "3..63";
                      }
                    }
                  }
                }
              }
            }
          }
        }
      }
      leaf mtu {
        tailf:info
          "Set IP Maximum Transmission Unit";
        type uint16 {
          tailf:info
            "<68-9198>;;MTU (bytes)";
          range "68..9198";
        }
      }
      container nat {
        tailf:info
          "NAT interface commands";
        leaf allow-static-host {
          tailf:info
            "Allow static-ip clients";
          type empty;
        }
        leaf enable {
          tailf:info
            "Enable Address Translation (NVI)";
          type empty;
        }
        choice nat-choice {
          leaf inside {
            tailf:info
              "Inside interface for address translation";
            type empty;
          }
          leaf outside {
            tailf:info
              "Outside interface for address translation";
            type empty;
          }
        }
      }
    }
    container ipv6 {
      tailf:info
        "IPv6 interface subcommands";
      container address {
        tailf:info
          "Configure IPv6 address on interface";
        choice address-choice {
          case autoconfig-case {
            container autoconfig {
              tailf:info
                "Obtain address using autoconfiguration";
              presence "true";
              leaf default {
                tailf:info
                  "Insert default route";
                type empty;
              }
            }
          }
          case manual-case {
            list prefix-list {
              tailf:cli-drop-node-name;
              tailf:cli-suppress-mode;
              tailf:cli-delete-when-empty;
              key "prefix";
              leaf prefix {
                type ios:ncs_rpc_notif_ipv6-prefix;
              }
              leaf anycast {
                tailf:info
                  "Configure as an anycast";
                tailf:cli-full-command;
                type empty;
              }
              leaf eui-64 {
                tailf:info
                  "Use eui-64 interface identifier";
                tailf:cli-full-command;
                type empty;
              }
            }
          }
        }
      }
      leaf enable {
        tailf:info
          "Enable IPv6 on interface";
        type empty;
      }
      container ospf {
        tailf:info
          "OSPF interface commands";
        list process {
          tailf:cli-suppress-mode;
          tailf:cli-delete-when-empty;
          tailf:cli-drop-node-name;
          tailf:cli-compact-syntax;
          tailf:cli-sequence-commands {
            tailf:cli-reset-siblings;
          }
          key "id";
          leaf id {
            type uint16 {
              tailf:info
                "<1-65535>;;Process ID";
              range "1..65535";
            }
          }
          leaf area {
            tailf:info
              "Set the OSPF area ID";
            type union {
              type uint32 {
                tailf:info
                  "<0-4294967295>;;OSPF area ID as a decimal value";
                range "0..4294967295";
              }
              type inet:ipv4-address {
                tailf:info
                  "A.B.C.D;;OSPF area ID in IP address format";
              }
            }
          }
          leaf instance {
            tailf:info
              "Set the OSPF instance";
            type union {
              type uint8 {
                tailf:info
                  "<0-31>;;Instance ID";
                range "0..31";
              }
              type uint8 {
                tailf:info
                  "<32-255>;;Instance ID (DEPRECATED!)";
                range "32..255";
              }
            }
          }
        }
        container bfd {
          tailf:info
            "Enable BFD on this interface";
          presence "true";
          leaf disable {
            tailf:info
              "Disable BFD on this interface";
            type empty;
          }
        }
        leaf cost {
          tailf:info
            "Route cost of this interface";
          type uint16 {
            tailf:info
              "<1-65535>;;Route cost of this interface";
            range "1..65535";
          }
        }
        container database-filter {
          tailf:info
            "Filter OSPF LSA during synchronization and flooding";
          choice database {
            leaf all {
              tailf:info
                "Filter all LSA";
              type enumeration {
                enum "out" {
                  tailf:info
                    "Outgoing LSA";
                }
              }
            }
            leaf disable {
              tailf:info
                "Disable LSA Filter on this interface";
              type empty;
            }
          }
        }
        leaf dead-interval {
          tailf:info
            "Interval after which a neighbor is declared dead";
          type uint16 {
            tailf:info
              "<1-65535>;;Seconds";
            range "1..65535";
          }
        }
        container demand-circuit {
          tailf:info
            "OSPF demand circuit";
          presence "true";
          leaf disable {
            tailf:info
              "Disable demand circuit on this interface";
            type empty;
          }
        }
        container flood-reduction {
          tailf:info
            "OSPF Flood Reduction";
          presence "true";
          leaf disable {
            tailf:info
              "Disable Flood Reduction on this interface";
            type empty;
          }
        }
        leaf hello-interval {
          tailf:info
            "Time between HELLO packets";
          type uint16 {
            tailf:info
              "<1-65535>;;Seconds";
            range "1..65535";
          }
        }
        container mtu-ignore {
          tailf:info
            "Ignores the MTU in DBD packets";
          presence "true";
          leaf disable {
            tailf:info
              "Disable Ingore MTU on this interface";
            type empty;
          }
        }
        leaf priority {
          tailf:info
            "Router priority";
          type uint16 {
            tailf:info
              "<0-255>;;Priority";
            range "0..255";
          }
        }
        leaf retransmit-interval {
          tailf:info
            "Time between retransmitting lost link state advertisements";
          type uint16 {
            tailf:info
              "<1-65535>;;Seconds";
            range "1..65535";
          }
        }
        leaf transmit-delay {
          tailf:info
            "Link state transmit delay";
          type uint16 {
            tailf:info
              "<1-65535>;;Seconds";
            range "1..65535";
          }
        }
      }
      leaf mtu {
        tailf:info
          "Set IPv6 Maximum Transmission Unit";
        type uint16 {
          tailf:info
            "<1280-9198>;;MTU (bytes)";
          range "1280..9198";
        }
      }
    }
    leaf load-interval {
      tailf:info
        "Specify interval for load calculation for an interface";
      type uint16 {
        tailf:info
          "<30-600>;;Load interval delay in seconds";
        range "0..600";
      }
    }
    leaf max-reserved-bandwidth {
      tailf:info
        "Maximum Reservable Bandwidth on an Interface";
      tailf:cli-full-command;
      type uint8 {
        tailf:info
          "<1-100>;;Max. reservable bandwidth as percent of interface bandwidth";
        range "1..100";
      }
    }
    container mls {
      tailf:info
        "mls sub/interface commands";
      container qos {
        tailf:info
          "qos command keyword";
        leaf channel-consistency {
          tailf:info
            "enable or disable qos consistency checks";
          tailf:cli-full-command;
          tailf:cli-boolean-no;
          tailf:cli-trim-default;
          type boolean;
          default "true";
        }
        leaf trust {
          tailf:info
            "trust keyword";
          tailf:cli-full-command;
          type enumeration {
            enum "cos" {
              tailf:info
                "cos keyword";
            }
            enum "dscp" {
              tailf:info
                "dscp keyword";
            }
            enum "ip-precedence" {
              tailf:info
                "ip-precedence keyword";
            }
          }
        }
        leaf vlan-based {
          tailf:info
            "vlan-based keyword";
          tailf:cli-full-command;
          type empty;
        }
      }
    }
    leaf mtu {
      tailf:info
        "Set the interface Maximum Transmission Unit (MTU)";
      tailf:cli-full-command;
      type uint16 {
        range "64..18000";
        tailf:info
          "<64-18000>;;MTU size in bytes";
      }
    }
    container power {
      container inline {
        leaf consumption {
          tailf:cli-full-command;
          type uint16 {
            range "4000..15400";
          }
        }
      }
    }
    container service-policy {
      tailf:info
        "Configure QoS Service Policy";
      leaf history {
        tailf:cli-full-command;
        tailf:info
          "Keep history of QoS metrics";
        type empty;
      }
      leaf input {
        tailf:cli-full-command;
        tailf:info
          "Assign policy-map to the input of an interface";
        type string {
          tailf:info
            "WORD;;policy-map name";
        }
        // NCS drop tailf-common:non-strict-leafref statement
      }
      leaf output {
        tailf:cli-full-command;
        tailf:info
          "Assign policy-map to the output of an interface";
        type string {
          tailf:info
            "WORD;;policy-map name";
        }
        // NCS drop tailf-common:non-strict-leafref statement
      }
      container type {
        tailf:info
          "Configure CPL Service Policy";
        container performance-monitor {
          tailf:info
            "Configure media monitor service-policy type";
          tailf:cli-sequence-commands;
          tailf:cli-compact-syntax;
          leaf direction {
            tailf:cli-drop-node-name;
            type enumeration {
              enum "input" {
                tailf:info
                  "Assign policy-map to the input of an interfcae";
              }
              enum "output" {
                tailf:info
                  "Assign policy-map to the output of an interfcae";
              }
            }
          }
          leaf name {
            tailf:cli-drop-node-name;
            type string {
              tailf:info
                "WORD;;policy-map name";
            }
            // NCS drop tailf-common:non-strict-leafref statement
          }
        }
      }
    }
    leaf shutdown {
      tailf:info
        "Shutdown the selected interface";
      tailf:cli-full-command;
      type empty;
    }
    container standby {
      tailf:info
        "HSRP interface configuration commands";
      leaf version {
        tailf:info
          "HSRP version";
        tailf:cli-full-command;
        type enumeration {
          tailf:info
            "<1-2>;;Version number";
          enum "1";
          enum "2";
        }
      }
      leaf bfd {
        tailf:info
          "Enable HSRP BFD";
        type empty;
      }
      container delay {
        tailf:info
          "HSRP initialisation delay";
        tailf:cli-compact-syntax;
        leaf minimum {
          tailf:info
            "Minimum delay";
          type uint16 {
            tailf:info
              "<0-10000>;;Delay in seconds";
            range "0..10000";
          }
        }
        leaf reload {
          tailf:info
            "Delay after reload";
          type uint16 {
            tailf:info
              "<0-10000>;;Delay in seconds";
            range "0..10000";
          }
        }
      }
      leaf mac-refresh {
        tailf:info
          "Refresh MAC cache on switch by periodically sending packet from virtual mac address";
        type uint8 {
          tailf:info
            "<0-255>;;Interval to refresh MAC cache";
          range "0..255";
        }
      }
      container use-bia {
        tailf:info
          "HSRP uses interface's burned in address";
        presence "true";
        container scope {
          tailf:info
            "Specify the scope of use-bia";
          leaf interface {
            tailf:info
              "Use-bia applies to all groups on this interface or sub-interface";
            type empty;
          }
        }
      }
      list standby-list {
        tailf:cli-drop-node-name;
        tailf:cli-suppress-mode;
        tailf:cli-delete-when-empty;
        tailf:cli-incomplete-command;
        key "group-number";
        leaf group-number {
          tailf:cli-suppress-range;
          type uint16 {
            tailf:info
              "<0-255>;;group number";
          }
        }
        container authentication {
          tailf:info
            "Authentication";
          choice auth {
            leaf word {
              tailf:cli-drop-node-name;
              tailf:cli-disallow-value "md5|text";
              type string {
                tailf:info
                  "WORD;;Plain text authentication string (8 chars max)";
              }
            }
            container md5 {
              tailf:info
                "Use MD5 authentication";
              leaf key-chain {
                tailf:info
                  "Set key chain";
                type string {
                  tailf:info
                    "WORD;;Name of key-chain";
                }
              }
              container key-string {
                tailf:info
                  "Set key string";
                tailf:cli-compact-syntax;
                tailf:cli-sequence-commands {
                  tailf:cli-reset-siblings;
                }
                leaf encrypt {
                  tailf:cli-drop-node-name;
                  type enumeration {
                    enum "0" {
                      tailf:info
                        "Specifies an UNENCRYPTED key string will follow";
                    }
                    enum "7" {
                      tailf:info
                        "Specifies a HIDDEN key string will follow";
                    }
                  }
                }
                leaf string {
                  tailf:cli-drop-node-name;
                  type string {
                    tailf:info
                      "WORD;;Key string (64 chars max)";
                  }
                }
                leaf timeout {
                  tailf:info
                    "Set timeout";
                  type uint16 {
                    tailf:info
                      "<0-32767>;;Timeout until only accepting new key (seconds)";
                    range "0..32767";
                  }
                }
              }
            }
            leaf text {
              tailf:info
                "Plain text authentication";
              type string {
                tailf:info
                  "WORD;;Plain text authentication string (8 chars max)";
              }
            }
          }
        }
        leaf follow {
          tailf:info
            "Name of HSRP group to follow";
          type string {
            tailf:info
              "WORD;;name string (25 chars. max)";
          }
        }
        container ip {
          tailf:info
            "Enable HSRP and set the virtual IP address";
          tailf:cli-sequence-commands;
          tailf:cli-compact-syntax;
          presence "true";
          leaf address {
            tailf:cli-drop-node-name;
            type inet:ipv4-address {
              tailf:info
                "A.B.C.D;;Virtual IP address";
            }
          }
          leaf secondary {
            tailf:info
              "Make this IP address a secondary virtual IP address";
            type empty;
          }
        }
        leaf ipv6 {
          tailf:info
            "Enable HSRP IPv6";
          type union {
            type inet:ipv6-address {
              tailf:info
                "X:X:X:X::X;;IPv6 link-local address";
            }
            type ios:ncs_rpc_notif_ipv6-prefix;
            type enumeration {
              enum "autoconfig" {
                tailf:info
                  "Obtain address using autoconfiguration";
              }
            }
          }
        }
        leaf mac-address {
          tailf:info
            "Virtual MAC address";
          type string {
            tailf:info
              "H.H.H;;MAC address";
          }
        }
        leaf name {
          tailf:info
            "Redundancy name string";
          tailf:cli-full-command;
          type string {
            tailf:info
              "WORD;;name string";
          }
        }
        container preempt {
          tailf:info
            "Overthrow lower priority Active routers";
          presence "true";
          container delay {
            tailf:info
              "Wait before preempting";
            tailf:cli-compact-syntax;
            leaf minimum {
              tailf:info
                "Delay at least this long";
              type uint16 {
                tailf:info
                  "<0-3600>;;Number of seconds for minimum delay";
                range "0..3600";
              }
            }
            leaf reload {
              tailf:info
                "Delay after reload";
              type uint16 {
                tailf:info
                  "<0-3600>;;Number of seconds for reload delay";
                range "0..3600";
              }
            }
            leaf sync {
              tailf:info
                "Wait for IP redundancy client";
              type uint16 {
                tailf:info
                  "<0-3600>;;Number of seconds for sync delay";
                range "0..3600";
              }
            }
          }
        }
        leaf priority {
          tailf:info
            "Priority level";
          tailf:cli-full-command;
          type uint8 {
            tailf:info
              "<0-255>;;Priority value";
          }
        }
        container redirect {
          tailf:info
            "Configure sending of ICMP Redirect messages with an HSRP virtual IP address as the gateway IP address";
          container advertisement {
            tailf:info
              "Redirect advertisement messages";
            container authentication {
              tailf:info
                "Authentication";
              container md5 {
                tailf:info
                  "Use MD5 authentication";
                leaf key-chain {
                  tailf:info
                    "Set key chain";
                  type string {
                    tailf:info
                      "WORD;;Name of key-chain";
                  }
                }
                container key-string {
                  tailf:info
                    "Set key string";
                  tailf:cli-compact-syntax;
                  tailf:cli-sequence-commands {
                    tailf:cli-reset-siblings;
                  }
                  leaf encrypt {
                    tailf:cli-drop-node-name;
                    type enumeration {
                      enum "0" {
                        tailf:info
                          "Specifies an UNENCRYPTED key string will follow";
                      }
                      enum "7" {
                        tailf:info
                          "Specifies a HIDDEN key string will follow";
                      }
                    }
                  }
                  leaf string {
                    tailf:cli-drop-node-name;
                    type string {
                      tailf:info
                        "WORD;;Key string (64 chars max)";
                    }
                  }
                  leaf timeout {
                    tailf:info
                      "Set timeout";
                    type uint16 {
                      tailf:info
                        "<0-32767>;;Timeout until only accepting new key (seconds)";
                      range "0..32767";
                    }
                  }
                }
              }
            }
          }
          container timers {
            tailf:info
              "Adjust redirect timers";
            tailf:cli-compact-syntax;
            tailf:cli-sequence-commands {
              tailf:cli-reset-siblings;
            }
            leaf advertisement {
              tailf:cli-drop-node-name;
              type uint16 {
                tailf:info
                  "<10-180>;;Passive router advertisement interval in seconds";
                range "10..180";
              }
            }
            leaf holddown {
              tailf:cli-drop-node-name;
              type uint16 {
                tailf:info
                  "<30-3600>;;Passive router holddown interval in seconds";
                range "30..3600";
              }
            }
          }
          leaf unknown {
            tailf:info
              "Redirect to non-HSRP routers";
            type empty;
          }
        }
        container timers {
          tailf:info
            "Hello and hold timers";
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                tailf:cli-incomplete-command;
                type uint8 {
                  tailf:info
                    "<1-254>;;Hello interval in seconds";
                  range "1..254";
                }
              }
              leaf msec {
                tailf:info
                  "Specify hello interval in milliseconds";
                tailf:cli-incomplete-command;
                type uint16 {
                  tailf:info
                    "<15-999>;;Hello interval in milliseconds";
                  range "15..999";
                }
              }
            }
          }
          container hold-time {
            tailf:cli-drop-node-name;
            tailf:cli-flatten-container;
            tailf:cli-compact-syntax;
            choice hold-time-choice {
              leaf seconds {
                tailf:cli-drop-node-name;
                type uint8 {
                  tailf:info
                    "<1-255>;;Hold time in seconds";
                  range "1..255";
                }
              }
              leaf msec {
                tailf:info
                  "Specify hold time in milliseconds";
                type uint16 {
                  tailf:info
                    "<50-3000>;;Hello interval in milliseconds";
                  range "50..3000";
                }
              }
            }
          }
        }
      }
    }
    container storm-control {
      tailf:info
        "storm configuration";
      container action {
        tailf:info
          "Action to take for storm..control;";
        leaf level {
          tailf:info
            "Set storm suppression level on this interface";
          type decimal64 {
            fraction-digits 2;
            tailf:info
              "<0-100>;;Enter Integer part of level as percentage of bandwidth";
            range "0..100";
          }
        }
      }
      container broadcast {
        tailf:info
          "Broadcast address storm control";
        leaf level {
          tailf:info
            "Set storm suppression level on this interface";
          type decimal64 {
            fraction-digits 2;
            tailf:info
              "<0-100>;;Enter Integer part of level as percentage of bandwidth";
            range "0..100";
          }
        }
      }
      container multicast {
        tailf:info
          "Multicast address storm control";
        leaf level {
          tailf:info
            "Set storm suppression level on this interface";
          type decimal64 {
            fraction-digits 2;
            tailf:info
              "<0-100>;;Enter Integer part of level as percentage of bandwidth";
            range "0..100";
          }
        }
      }
      container unicast {
        tailf:info
          "Unicast address storm control";
        leaf level {
          tailf:info
            "Set storm suppression level on this interface";
          type decimal64 {
            fraction-digits 2;
            tailf:info
              "<0-100>;;Enter Integer part of level as percentage of bandwidth";
            range "0..100";
          }
        }
      }
    }
    container wrr-queue {
      tailf:info
        "Configure weighted round-robin xmt queues";
      container bandwidth {
        tailf:info
          "Configure WRR minimum bandwidth with weights or percentages";
        tailf:cli-compact-syntax;
        tailf:cli-sequence-commands {
          tailf:cli-reset-siblings;
        }
        choice bandwidth-choice {
          case a {
            leaf weight-1 {
              tailf:cli-drop-node-name;
              type uint8 {
                tailf:info
                  "<0-255>;;enter bandwidth weight";
                range "0..255";
              }
            }
            leaf weight-2 {
              tailf:cli-drop-node-name;
              type uint8 {
                tailf:info
                  "<0-255>;;enter bandwidth weight";
                range "0..255";
              }
            }
            leaf weight-3 {
              tailf:cli-drop-node-name;
              type uint8 {
                tailf:info
                  "<0-255>;;enter bandwidth weight";
                range "0..255";
              }
            }
            leaf weight-4 {
              tailf:cli-drop-node-name;
              type uint8 {
                tailf:info
                  "<0-255>;;enter bandwidth weight";
                range "0..255";
              }
            }
            leaf weight-5 {
              tailf:cli-drop-node-name;
              type uint8 {
                tailf:info
                  "<0-255>;;enter bandwidth weight";
                range "0..255";
              }
            }
            leaf weight-6 {
              tailf:cli-drop-node-name;
              type uint8 {
                tailf:info
                  "<0-255>;;enter bandwidth weight";
                range "0..255";
              }
            }
            leaf weight-7 {
              tailf:cli-drop-node-name;
              type uint8 {
                tailf:info
                  "<0-255>;;enter bandwidth weight";
                range "0..255";
              }
            }
          }
          case b {
            container percent {
              tailf:cli-compact-syntax;
              tailf:cli-sequence-commands {
                tailf:cli-reset-siblings;
              }
              leaf percent-1 {
                tailf:cli-drop-node-name;
                type uint8 {
                  tailf:info
                    "<0-100>;;enter bandwidth percent";
                  range "0..100";
                }
              }
              leaf percent-2 {
                tailf:cli-drop-node-name;
                type uint8 {
                  tailf:info
                    "<0-100>;;enter bandwidth percent";
                  range "0..100";
                }
              }
              leaf percent-3 {
                tailf:cli-drop-node-name;
                type uint8 {
                  tailf:info
                    "<0-100>;;enter bandwidth percent";
                  range "0..100";
                }
              }
              leaf percent-4 {
                tailf:cli-drop-node-name;
                type uint8 {
                  tailf:info
                    "<0-100>;;enter bandwidth percent";
                  range "0..100";
                }
              }
              leaf percent-5 {
                tailf:cli-drop-node-name;
                type uint8 {
                  tailf:info
                    "<0-100>;;enter bandwidth percent";
                  range "0..100";
                }
              }
              leaf percent-6 {
                tailf:cli-drop-node-name;
                type uint8 {
                  tailf:info
                    "<0-100>;;enter bandwidth percent";
                  range "0..100";
                }
              }
              leaf percent-7 {
                tailf:cli-drop-node-name;
                type uint8 {
                  tailf:info
                    "<0-100>;;enter bandwidth percent";
                  range "0..100";
                }
              }
            }
          }
        }
      }
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
      container queue-limit {
        tailf:info
          "Configure queue-limit";
        tailf:cli-compact-syntax;
        tailf:cli-sequence-commands {
          tailf:cli-reset-siblings;
        }
        leaf weight-a {
          tailf:cli-drop-node-name;
          type uint8 {
            tailf:info
              "<0-100>;;enter queue size weight";
            range "0..100";
          }
        }
        leaf weight-b {
          tailf:cli-drop-node-name;
          type uint8 {
            tailf:info
              "<0-100>;;enter queue size weight";
            range "0..100";
          }
        }
        leaf weight-c {
          tailf:cli-drop-node-name;
          type uint8 {
            tailf:info
              "<0-100>;;enter queue size weight";
            range "0..100";
          }
        }
      }
      container random-detect {
        tailf:info
          "Configure random-detect";
        list max-threshold {
          tailf:info
            "Max threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses ncs_rpc_notif_queue-size-grouping;
        }
        list min-threshold {
          tailf:info
            "Min threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses ncs_rpc_notif_queue-size-grouping;
        }
      }
      list threshold {
        tailf:info
          "Configure queue tail-drop thresholds";
        tailf:cli-suppress-mode;
        tailf:cli-delete-when-empty;
        tailf:cli-compact-syntax;
        tailf:cli-sequence-commands {
          tailf:cli-reset-siblings;
        }
        key "id";
        leaf id {
          type uint8 {
            tailf:info
              "<1-3>;;enter queue id";
            range "1..3";
          }
        }
        uses ncs_rpc_notif_queue-size-grouping;
      }
    }
    container priority-queue {
      tailf:info
        "Configure priority scheduling";
      container cos-map {
        tailf:info
          "Configure cos-map for a queue";
        tailf:cli-compact-syntax;
        tailf:cli-sequence-commands {
          tailf:cli-reset-siblings;
        }
        leaf id {
          tailf:cli-drop-node-name;
          type uint8;
        }
        leaf-list cos-values {
          tailf:cli-drop-node-name;
          tailf:cli-flat-list-syntax;
          max-elements 8;
          type uint8 {
            tailf:info
              "<0-7>;;cos values separated by spaces (up to 8 values total)";
            range "0..7";
          }
        }
      }
      leaf out {
        tailf:info
          "egress priority queue";
        tailf:cli-full-command;
        type empty;
      }
    }
    container rep {
      tailf:info
        "Resilient Ethernet Protocol characteristics";
      container block {
        tailf:info
          "Block port & VLANs for VLAN Load-balancing";
        container port {
          tailf:info
            "Specify port for VLAN Load-balancing";
          tailf:cli-sequence-commands {
            tailf:cli-reset-siblings;
          }
          tailf:cli-compact-syntax;
          choice port-choice {
            leaf neighbor-offset {
              tailf:cli-drop-node-name;
              type int16 {
                tailf:info
                  "<-256 - 256>;;Neighbor offset";
                range "-256..256";
              }
            }
            leaf id {
              tailf:info
                "REP port ID";
              type string {
                tailf:info
                  "WORD;;REP port ID (16 digit hexadecimal number)";
              }
            }
            leaf preferred {
              tailf:info
                "Preferred flag";
              type empty;
            }
          }
          leaf vlan {
            tailf:info
              "VLANs to block";
            type union {
              type string {
                tailf:info
                  "WORD;;VLAN list (1-4094) ex: 1-65,72,300-320";
              }
              type enumeration {
                enum "all" {
                  tailf:info
                    "All VLANs";
                }
              }
            }
          }
        }
      }
      container preempt {
        tailf:info
          "Preemption options";
        leaf delay {
          tailf:info
            "Delay timer in seconds";
          type uint16 {
            tailf:info
              "<15-300>;;number of seconds before automatic preemption takes place";
            range "15..300";
          }
        }
      }
      container segment {
        tailf:info
          "REP segment ID";
        tailf:cli-compact-syntax;
        tailf:cli-sequence-commands {
          tailf:cli-reset-siblings;
        }
        leaf id {
          tailf:cli-drop-node-name;
          type uint16 {
            tailf:info
              "<1-1024>;;Between 1 and 1024";
            range "1..1024";
          }
        }
        leaf edge {
          tailf:info
            "Edge Port";
          tailf:cli-optional-in-sequence;
          type empty;
        }
        leaf primary {
          tailf:info
            "Primary Edge Port";
          tailf:cli-optional-in-sequence;
          when '../edge' {
            tailf:xpath-root 3;
            tailf:dependency "../edge";
          }
          type empty;
        }
        leaf preferred {
          tailf:info
            "Preferred Alternate Port";
          type empty;
        }
      }
      container stcn {
        tailf:info
          "Segment Topology Change Notification";
        leaf segment {
          tailf:info
            "for REP segment";
          type string {
            tailf:info
              "WORD;;segment ID list (1-1024) ex: 1-3,6-9";
          }
        }
        leaf stp {
          tailf:info
            "for STP network";
          type empty;
        }
      }
    }
    container rcv-queue {
      tailf:info
        "Configure receive queue(s)";
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
    }
    container udld {
      tailf:info
        "Configure UDLD enabled or disabled and ignore global UDLD setting";
      container port {
        tailf:info
          "Enable UDLD protocol on this interface despite global UDLD setting";
        tailf:cli-delete-when-empty;
        presence "true";
        choice port-choice {
          leaf aggressive {
            tailf:info
              "Enable UDLD protocol in aggressive mode on this interface despite global UDLD setting";
            type empty;
          }
          leaf disable {
            tailf:info
              "Disable UDLD protocol on this interface despite global UDLD setting";
            type empty;
          }
        }
      }
    }
    container peer {
      tailf:info
        "Peer parameters for point to point interfaces";
      container default {
        tailf:info
          "Specify default parameters";
        container ip {
          tailf:info
            "Specify default IP parameters";
          container address {
            tailf:info
              "Specify default IP address";
            choice address-choice {
              leaf dhcp {
                tailf:info
                  "Use DHCP proxy client mechanism to allocate a peer IP address";
                type empty;
              }
              container dhcp-pool {
                tailf:info
                  "Use local DHCP pools to allocate a peer IP address";
                presence "true";
                leaf pools {
                  tailf:cli-drop-node-name;
                  tailf:cli-multi-value;
                  type string {
                    tailf:info
                      "LINE;;List of one or more DHCP address pools";
                  }
                }
              }
              container pool {
                tailf:info
                  "Use IP pool mechanism to allocate a peer IP address";
                presence "true";
                leaf pools {
                  tailf:cli-drop-node-name;
                  tailf:cli-multi-value;
                  type string {
                    tailf:info
                      "LINE;;List of one or more DHCP address pools";
                  }
                }
              }
            }
          }
        }
      }
    }
  }

  grouping ncs_rpc_notif_interface-ethernet-grouping {
    container carrier-delay {
      tailf:info
        "Specify delay for interface transitions";
      choice delay-choice {
        leaf seconds {
          tailf:cli-drop-node-name;
          type uint8 {
            tailf:info
              "<0-60>  Carrier Transitions delay seconds";
            range "0..60";
          }
        }
        leaf msec {
          tailf:info
            "delay specified in milliseconds";
          type uint16 {
            tailf:info
              "<0-1000>;;Carrier Transitions delay milliseconds";
            range "0..1000";
          }
        }
      }
    }
    container channel-group {
      tailf:info
        "Add this interface to an Etherchannel group";
      tailf:cli-sequence-commands {
        tailf:cli-reset-siblings;
      }
      tailf:cli-compact-syntax;
      leaf number {
        tailf:cli-drop-node-name;
        tailf:cli-incomplete-command;
        type uint16 {
          tailf:info
            "<1-512>;;Channel group number";
          range "1..512";
        }
      }
      leaf mode {
        tailf:info
          "Etherchannel Mode of the interface";
        type enumeration {
          enum "active" {
            tailf:info
              "Enable LACP unconditionally";
          }
          enum "auto" {
            tailf:info
              "Enable PAgP only if a PAgP device is detected";
          }
          enum "desirable" {
            tailf:info
              "Enable PAgP unconditionally";
          }
          enum "on" {
            tailf:info
              "Enable Etherchannel only";
          }
          enum "passive" {
            tailf:info
              "Enable LACP only if a LACP device is detected";
          }
        }
      }
    }
    leaf channel-protocol {
      tailf:info
        "Select the channel protocol (LACP, PAgP)";
      type enumeration {
        enum "lacp" {
          tailf:info
            "Prepare interface for LACP protocol";
        }
        enum "pagp" {
          tailf:info
            "Prepare interface for PAgP protocol";
        }
      }
    }
    container ethernet {
      tailf:info
        "Ethernet interface parameters";
      container oam {
        tailf:info
          "To enable Ethernet Link OAM";
        presence "true";
        leaf max-rate {
          type uint8 {
            tailf:info
              "Maximum number of OAM PDUs sent per second";
            range "1..10";
          }
        }
        leaf min-rate {
          type uint8 {
            tailf:info
              "Minimum transmission rate in seconds";
            range "1..10";
          }
        }
        leaf mode {
          type enumeration {
            enum "active" {
              tailf:info
                "Active OAM client mode";
            }
            enum "passive" {
              tailf:info
                "Passive OAM client mode";
            }
          }
        }
        leaf timeout {
          type uint8 {
            tailf:info
              "OAM client timeout in seconds";
            range "2..30";
          }
        }
      }
    }
    leaf negotiation {
      tailf:info
        "Select autonegotiation mode";
      type enumeration {
        tailf:info
          "Enable link autonegotiation";
        enum "auto";
      }
    }
    leaf duplex {
      tailf:info
        "Configure duplex operation.";
      type enumeration {
        enum "auto" {
          tailf:code-name "duplex_auto";
          tailf:info
            "Enable AUTO duplex configuration";
        }
        enum "full" {
          tailf:code-name "duplex_full";
          tailf:info
            "Force full duplex operation";
        }
        enum "half" {
          tailf:code-name "duplex_half";
          tailf:info
            "Force half-duplex operation";
        }
      }
    }
    leaf speed {
      tailf:info
        "Configure speed operation.";
      type enumeration {
        enum "10" {
          tailf:info
            "Force 10 Mbps operation";
        }
        enum "100" {
          tailf:info
            "Force 100 Mbps operation";
        }
        enum "1000" {
          tailf:info
            "Enable AUTO speed configuration";
        }
        enum "nonegotiate";
        enum "auto" {
          tailf:info
            "Enable AUTO speed configuration";
        }
      }
    }
    container xconnect {
      tailf:info
        "Xconnect commands";
      tailf:cli-sequence-commands;
      tailf:cli-compact-syntax;
      leaf address {
        tailf:cli-drop-node-name;
        tailf:cli-incomplete-command;
        type inet:ipv4-address {
          tailf:info
            "A.B.C.D;;IP address of peer";
        }
      }
      leaf vcid {
        tailf:cli-drop-node-name;
        tailf:cli-incomplete-command;
        type uint32 {
          tailf:info
            "<1-4294967295>;;Enter VC ID value";
          range "1..4294967295";
        }
      }
      leaf encapsulation {
        tailf:info
          "Data encapsulation method";
        tailf:cli-optional-in-sequence;
        type enumeration {
          enum "mpls" {
            tailf:code-name "encap_mpls";
            tailf:info
              "Use MPLS encapsulation";
          }
          enum "l2tpv3" {
            tailf:info
              "Use L2TPv3 encapsulation";
          }
        }
      }
      leaf manual {
        tailf:info
          "Manually configure L2TP session parameters";
        tailf:cli-optional-in-sequence;
        when "../encapsulation = 'l2tpv3'" {
          tailf:xpath-root 3;
        }
        type empty;
      }
      leaf sequence {
        tailf:info
          "Configure sequencing options for xconnect";
        tailf:cli-full-command;
        tailf:cli-optional-in-sequence;
        when "../encapsulation = 'l2tpv3'" {
          tailf:xpath-root 3;
        }
        type enumeration {
          enum "both" {
            tailf:info
              "Transmit and receive sequence numbers";
          }
          enum "receive" {
            tailf:info
              "Receive sequence numbers";
          }
          enum "transmit" {
            tailf:info
              "Transmit sequence numbers";
          }
        }
      }
      leaf pw-class {
        tailf:info
          "Pseudowire-class to use for encapsulation and protocol configuration";
        type string {
          tailf:info
            "WORD;;Pseudowire-class name";
        }
      }
    }
    container pppoe {
      tailf:info
        "pppoe interface subcommands";
      container enable {
        tailf:info
          "Enable pppoe";
        presence "true";
        leaf group {
          tailf:info
            "attach a BBA group";
          type union {
            type string {
              tailf:info
                "WORD;;BBA Group name";
            }
            type enumeration {
              enum "global" {
                tailf:info
                  "Attach global PPPoE group";
              }
            }
          }
        }
      }
      leaf max-sessions {
        tailf:info
          "Maximum PPPOE sessions";
        type uint16 {
          tailf:info
            "<1-4085>;;Maximum PPPOE sessions";
          range "1..4085";
        }
      }
    }
  }

  grouping ncs_rpc_notif_interface-zone-member-grouping {
    container zone-member {
      tailf:info
        "Apply zone name";
      leaf security {
        tailf:info
          "Security zone";
        type string;
        // NCS drop tailf-common:non-strict-leafref statement
      }
    }
  }

  grouping ncs_rpc_notif_interface-pointtopoint-grouping {
    container ppp {
      tailf:info
        "Point-to-Point Protocol";
      leaf accounting {
        tailf:info
          "Set PPP network accounting method";
        type union {
          type string {
            tailf:info
              "WORD;;Named accounting list.";
          }
          type enumeration {
            enum "default" {
              tailf:info
                "The default accounting list.";
            }
          }
        }
      }
      container authentication {
        tailf:info
          "Set PPP link authentication method";
        tailf:cli-compact-syntax;
        tailf:cli-sequence-commands;
        leaf method {
          tailf:cli-drop-node-name;
          type enumeration {
            enum "chap" {
              tailf:info
                "Challenge Handshake Authentication Protocol (CHAP)";
            }
            enum "eap" {
              tailf:info
                "Extensible Authentication Protocol (EAP)";
            }
            enum "ms-chap" {
              tailf:info
                "Microsoft Challenge Handshake Authentication Protocol (MS-CHAP)";
            }
            enum "ms-chap-v2" {
              tailf:info
                "Microsoft CHAP Version 2 (MS-CHAP-V2)";
            }
            enum "pap" {
              tailf:info
                "Password Authentication Protocol (PAP)";
            }
          }
        }
        leaf list-name {
          tailf:cli-break-sequence-commands;
          tailf:cli-drop-node-name;
          type string {
            tailf:info
              "WORD;;Use an authentication list with this name";
          }
          tailf:cli-disallow-value "(callback)|(callin)|(callout)|(default)|(eap)|(ms-chap)|(ms-chap-v2)|(one-time)|(optional)|(pap)";
        }
        leaf chap {
          when "not(../method = 'chap')" {
            tailf:xpath-root 3;
            tailf:dependency "../method";
          }
          tailf:info
            "Challenge Handshake Authentication Protocol (CHAP)";
          type empty;
        }
        leaf callback {
          tailf:info
            "Authenticate remote on callback only";
          type empty;
        }
        leaf callin {
          tailf:info
            "Authenticate remote on incoming call only";
          type empty;
        }
        leaf callout {
          tailf:info
            "Authenticate remote on outgoing call only";
          type empty;
        }
        leaf default {
          tailf:info
            "Use the default authentication list";
          type empty;
        }
        leaf eap {
          when "not(../method = 'eap')" {
            tailf:xpath-root 3;
            tailf:dependency "../method";
          }
          tailf:info
            "Extensible Authentication Protocol (EAP)";
          type empty;
        }
        leaf ms-chap {
          when "not(../method = 'ms-chap')" {
            tailf:xpath-root 3;
            tailf:dependency "../method";
          }
          tailf:info
            "Microsoft Challenge Handshake Authentication Protocol (MS-CHAP)";
          type empty;
        }
        leaf ms-chap-v2 {
          when "not(../method = 'ms-chap-v2')" {
            tailf:xpath-root 3;
            tailf:dependency "../method";
          }
          tailf:info
            "Microsoft CHAP Version 2 (MS-CHAP-V2)";
          type empty;
        }
        leaf one-time {
          tailf:info
            "Allow use of username*OTP for one-time passwords";
          type empty;
        }
        leaf optional {
          tailf:info
            "Allow peer to refuse to authenticate";
          type empty;
        }
        leaf pap {
          when "not(../method = 'pap')" {
            tailf:xpath-root 3;
            tailf:dependency "../method";
          }
          tailf:info
            "Password Authentication Protocol (PAP)";
          type empty;
        }
      }
      leaf authorization {
        tailf:info
          "Set PPP network authorization method";
        type union {
          type string {
            tailf:info
              "WORD;;Named authorization list.";
          }
          type enumeration {
            enum "default" {
              tailf:info
                "The default authorization list.";
            }
          }
        }
      }
      container ipcp {
        tailf:info
          "Set IPCP negotiation options";
        container dns {
          tailf:info
            "Specify DNS negotiation options";
          tailf:cli-compact-syntax;
          tailf:cli-sequence-commands;
          leaf primary {
            tailf:cli-drop-node-name;
            type inet:ipv4-address {
              tailf:info
                "A.B.C.D;;Primary DNS IP address";
            }
          }
        }
      }
      container multilink {
        tailf:info
          "Make interface multilink capable";
        tailf:cli-display-separated;
        presence "true";
        container links {
          tailf:info
            "Specify the limits on the number of links in a bundle";
          container minimum {
            tailf:info
              "Minimum number of links desired in the bundle";
            tailf:cli-compact-syntax;
            tailf:cli-sequence-commands {
              tailf:cli-reset-all-siblings;
            }
            leaf minimum-value {
              tailf:cli-drop-node-name;
              type uint8 {
                tailf:info
                  "<1-255>;;Specify minimum desired number of links in a bundle";
              }
            }
            leaf mandatory {
              tailf:info
                "Disable network layer until minimum number of links is reach";
              type empty;
            }
          }
        }
        leaf group {
          tailf:info
            "Put interface in a multilink bundle";
          type uint32 {
            tailf:info
              "<1-2147483647>;;Multilink group number";
            range "1..2147483647";
          }
        }
        container fragment {
          tailf:info
            "Specify fragmentation parameters";
          container delay {
            tailf:info
              "Specify the maximum delay for each fragment";
            tailf:cli-compact-syntax;
            tailf:cli-sequence-commands {
              tailf:cli-reset-siblings;
            }
            leaf delay-value {
              tailf:cli-drop-node-name;
              type uint16 {
                tailf:info
                  "<0-1000>;;Delay in milliseconds";
                range "0..1000";
              }
            }
            leaf additional-delay-value {
              tailf:cli-drop-node-name;
              type uint16 {
                tailf:info
                  "<1-999>;;Additional delay in microseconds";
                range "1..999";
              }
            }
          }
        }
      }
    }
  }

  grouping ncs_rpc_notif_crypto-pki-token-grouping {
    container removal {
      tailf:info
        "actions to take after token removal";
      leaf timeout {
        tailf:info
          "seconds after token removal at which keys from the token are cleared";
        type uint16 {
          tailf:info
            "<0-480>;;Token key timeout in seconds";
          range "0..480";
        }
      }
    }
  }

  grouping ncs_rpc_notif_max-path-grouping {
    container max-path {
      tailf:cli-drop-node-name;
      tailf:cli-compact-syntax;
      tailf:cli-sequence-commands {
        tailf:cli-reset-siblings;
      }
      leaf max {
        tailf:cli-drop-node-name;
        type uint16 {
          range "1..16";
          tailf:info
            "<1-16>;;Number of paths";
        }
        default "1";
      }
      leaf import {
        tailf:info
          "Maximum import paths";
        type uint16 {
          range "1..16";
          tailf:info
            "<1-16>;;Number of import paths";
        }
      }
    }
  }

  grouping ncs_rpc_notif_metric-route-map-grouping {
    leaf metric {
      tailf:cli-break-sequence-commands;
      tailf:info
        "Metric for redistributed routes";
      type uint32 {
        range "0..4294967295";
        tailf:info
          "<0-4294967295>;;Default metric";
      }
    }
    leaf route-map {
      tailf:info
        "Route map reference";
      type string {
        tailf:info
          "WORD;;Pointer to route-map entries";
      }
    }
  }

  grouping ncs_rpc_notif_route-map-metric-grouping {
    leaf route-map {
      tailf:info
        "Route map reference";
      type string {
        tailf:info
          "WORD;;Pointer to route-map entries";
      }
    }
    leaf metric {
      tailf:info
        "Metric for redistributed routes";
      type uint32 {
        range "0..4294967295";
        tailf:info
          "<0-4294967295>;;Default metric";
      }
    }
  }

  grouping ncs_rpc_notif_redistribute-isis-grouping {
    choice osi-ip-choice {
      leaf ip {
        tailf:info
          "Redistribution of IP dynamic routes";
        type empty;
      }
      leaf clns {
        tailf:info
          "Redistribution of OSI dynamic routes";
        type empty;
      }
    }
    leaf routes {
      tailf:cli-drop-node-name;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
    uses ncs_rpc_notif_metric-route-map-grouping;
  }

  grouping ncs_rpc_notif_bgp-address-family-grouping {
    container aggregate-address {
      tailf:info
        "Configure BGP aggregate entries";
      tailf:cli-compact-syntax;
      tailf:cli-sequence-commands {
        tailf:cli-reset-all-siblings;
      }
      leaf address {
        tailf:cli-drop-node-name;
        type inet:ipv4-address {
          tailf:info
            "A.B.C.D;;Aggregate address";
        }
      }
      leaf mask {
        tailf:cli-drop-node-name;
        type inet:ipv4-address {
          tailf:info
            "A.B.C.D;;Aggregate mask";
        }
      }
      leaf advertise-map {
        tailf:cli-break-sequence-commands;
        tailf:info
          "Set condition to advertise attribute";
        type string {
          tailf:info
            "WORD;;Route map to control attribute advertisement";
        }
      }
      leaf as-set {
        tailf:info
          "Generate AS set path information";
        type empty;
      }
      leaf attribute-map {
        type string {
          tailf:info
            "WORD;;Route map for parameter control";
        }
      }
      leaf as-override {
        tailf:info
          "Override matching AS-number while sending update";
        type empty;
      }
      leaf route-map {
        type string {
          tailf:info
            "WORD;;Route map for parameter control";
        }
      }
      leaf summary-only {
        tailf:info
          "Filter more specific routes from updates";
        type empty;
      }
      leaf suppress-map {
        tailf:info
          "Conditionally filter more specific routes from updates";
        type string {
          tailf:info
            "WORD;;Route map for suppression";
        }
      }
    }
    container bgp {
      tailf:info
        "BGP specific commands";
      leaf router-id {
        tailf:cli-full-command;
        tailf:info
          "Override configured router identifier (peers will reset)";
        type inet:ipv4-address {
          tailf:info
            "A.B.C.D;;Manually configured router identifier";
        }
      }
      leaf always-compare-med {
        tailf:info
          "Allow comparing MED from different neighbors";
        tailf:cli-full-command;
        type empty;
      }
      container bestpath {
        tailf:info
          "Change the default bestpath selection";
        leaf compare-routerid {
          tailf:cli-full-command;
          tailf:info
            "Compare router-id for identical EBGP paths";
          type empty;
        }
        container cost-community {
          tailf:info
            "cost community";
          leaf ignore {
            tailf:info
              "Ignore cost communities in bestpath selection";
            type empty;
          }
        }
        container med {
          tailf:info
            "MED attribute";
          choice med-choice {
            container confed {
              tailf:info
                "Compare MED among confederation paths";
              presence "Compare MED among confederation paths";
              leaf missing-at-worst {
                tailf:info
                  "Treat missing MED as the least preferred one";
                type empty;
              }
            }
            leaf missing-at-worst {
              tailf:info
                "Treat missing MED as the least preferred one";
              type empty;
            }
          }
        }
      }
      container client-to-client {
        tailf:info
          "Configure client to client route reflection";
        leaf reflection {
          tailf:info
            "reflection of routes allowed";
          type empty;
        }
      }
      leaf cluster-id {
        tailf:cli-full-command;
        type union {
          type uint32 {
            range "1..4294967295";
            tailf:info
              "<1-4294967295>;;Route-Reflector Cluster-id as 32 bit quantity";
          }
          type inet:ipv4-address {
            tailf:info
              "A.B.C.D;;Route-Reflector Cluster-id in IP address format";
          }
        }
      }
      container confederation {
        tailf:info
          "AS confederation parameters";
        leaf identifier {
          tailf:cli-full-command;
          tailf:info
            "as number";
          type uint16 {
            range "1..65535";
            tailf:info
              "<1-65535>;;Set routing domain confederation AS";
          }
        }
        container peers {
          tailf:info
            "Peer ASs in BGP confederation";
          presence "Peer ASs in BGP confederation";
          leaf-list peers-as {
            tailf:cli-drop-node-name;
            tailf:cli-flat-list-syntax;
            type uint16 {
              range "1..65535";
              tailf:info
                "AS number";
            }
          }
        }
      }
      container dampening {
        tailf:info
          "Enable route-flap dampening";
        presence "enable bgp route-flap dampening";
        choice dampening-choice {
          leaf route-map {
            tailf:info
              "Route-map to specify criteria for dampening";
            type string {
              tailf:info
                "WORD;;route-map name";
            }
          }
          container dampen {
            tailf:cli-drop-node-name;
            tailf:cli-compact-syntax;
            tailf:cli-sequence-commands;
            leaf half-life-time {
              tailf:cli-drop-node-name;
              tailf:cli-incomplete-command;
              type uint8 {
                range "1 .. 45";
                tailf:info
                  "<1-45>;;Half-life time for the penalty";
              }
            }
            leaf reuse-time {
              tailf:cli-drop-node-name;
              tailf:cli-incomplete-command;
              type uint16 {
                range "1 .. 20000";
                tailf:info
                  "<1-20000>;;Value to start reusing a route";
              }
            }
            leaf suppress-time {
              tailf:cli-drop-node-name;
              tailf:cli-incomplete-command;
              type uint16 {
                range "1 .. 20000";
                tailf:info
                  "<1-20000>;;Value to start suppressing a route";
              }
            }
            leaf max-suppress-time {
              tailf:cli-drop-node-name;
              type uint8 {
                range "1 .. 255";
                tailf:info
                  "<1-255>  Maximum duration to suppress a stable route";
              }
            }
          }
        }
      }
      container default {
        tailf:info
          "Configure BGP defaults";
        choice default-choice {
          leaf ipv4-unicast {
            tailf:info
              "Activate ipv4-unicast for a peer by default";
            tailf:cli-boolean-no;
            tailf:cli-trim-default;
            type boolean;
            default "true";
          }
          leaf local-preference {
            tailf:info
              "local preference (higher=more preferred)";
            type uint32 {
              range "1..4294967295";
              tailf:info
                "<0-4294967295>;;Configure default local preference value";
            }
          }
          leaf route-target {
            tailf:info
              "Control behavior based on Route-Target attributes";
            type enumeration {
              enum "filter" {
                tailf:info
                  "Control automatic VPN Route-Target filtering";
              }
            }
          }
        }
      }
      leaf deterministic-med {
        tailf:cli-full-command;
        tailf:info
          "Pick the best-MED path among paths advertised from the neighboring AS";
        type empty;
      }
      leaf dmzlink-bw {
        tailf:cli-full-command;
        tailf:info
          "Use DMZ Link Bandwidth as weight for BGP multipaths";
        type empty;
      }
      leaf enforce-first-as {
        tailf:cli-full-command;
        tailf:info
          "Enforce the first AS for EBGP routes(default)";
        type empty;
      }
      leaf fast-external-fallover {
        tailf:cli-full-command;
        tailf:info
          "Immediately reset session if a link to a directly connected external peer goes down";
        type empty;
      }
      container graceful-restart {
        tailf:info
          "Graceful restart capability parameters";
        presence "Graceful restart capability parameters";
        leaf restart-time {
          tailf:cli-full-command;
          tailf:info
            "Set the max time needed to restart and come back up";
          type uint16 {
            range "1..3600";
            tailf:info
              "<1-3600>;;Delay value (seconds)";
          }
        }
        leaf stalepath-time {
          tailf:info
            "Set the max time to hold onto restarting peer's stale paths";
          type uint16 {
            range "1..3600";
            tailf:info
              "<1-3600>;;Delay value (seconds)";
          }
        }
      }
      list inject-map {
        tailf:info
          "Routemap which specifies prefixes to inject";
        tailf:cli-compact-syntax;
        tailf:cli-sequence-commands;
        tailf:cli-incomplete-command;
        tailf:cli-delete-when-empty;
        key "name";
        leaf name {
          type string {
            tailf:info
              "WORD;;route-map name";
          }
        }
        leaf exist-map {
          tailf:info
            "Routemap which specifies exist condition";
          type string {
            tailf:info
              "WORD;;route-map name";
          }
        }
        leaf copy-attributes {
          tailf:info
            "Copy attributes from aggregate";
          type empty;
        }
      }
      leaf log-neighbor-changes {
        tailf:info
          "Log neighbor up/down and reset reason";
        tailf:cli-full-command;
        type empty;
      }
      leaf maxas-limit {
        tailf:info
          "Allow AS-PATH attribute from any neighbor imposing a limit on number of ASes";
        tailf:cli-full-command;
        type uint16 {
          range "1..2000";
          tailf:info
            "<1-2000>;;Number of ASes in the AS-PATH attribute";
        }
      }
      container nexthop {
        tailf:info
          "Nexthop tracking commands";
        container trigger {
          tailf:info
            "Nexthop triggering";
          leaf delay {
            tailf:cli-full-command;
            tailf:info
              "Set the delay to tigger nexthop tracking";
            type uint8 {
              range "0..100";
              tailf:info
                "<0-100>;;Delay value (seconds)";
            }
          }
          leaf enable {
            tailf:info
              "Enable nexthop tracking";
            tailf:cli-full-command;
            tailf:cli-boolean-no;
            type boolean;
            default "true";
          }
        }
      }
      leaf redistribute-internal {
        tailf:info
          "Allow redistribution of iBGP into IGPs (dangerous)";
        tailf:cli-full-command;
        type empty;
      }
      container regexp {
        tailf:info
          "Select regular expression engine";
        leaf deterministic {
          tailf:info
            "Enable bounded-execution-time regular expression engine";
          type empty;
        }
      }
      leaf scan-time {
        tailf:cli-full-command;
        tailf:info
          "Configure background scanner interval";
        type uint8 {
          range "5..60";
          tailf:info
            "<5-60>;;Scanner interval (seconds)";
        }
      }
      leaf soft-reconfig-backup {
        tailf:info
          "Use soft-reconfiguration inbound only when route-refresh is not negotiated";
        tailf:cli-full-command;
        type empty;
      }
      leaf suppress-inactive {
        tailf:info
          "Suppress routes that are not in the routing table";
        tailf:cli-full-command;
        type empty;
      }
      leaf update-delay {
        tailf:cli-full-command;
        tailf:info
          "Set the max initial delay for sending update";
        type uint16 {
          range "1..3600";
          tailf:info
            "<1-3600>;;Delay value (seconds)";
        }
      }
    }
    container default-information {
      tailf:info
        "Control distribution of default information";
      leaf originate {
        tailf:info
          "Distribute a default route";
        type empty;
      }
    }
    leaf default-metric {
      tailf:info
        "Set metric of redistributed routes";
      tailf:cli-full-command;
      type uint32 {
        range "1..4294967295";
        tailf:info
          "<1-4294967295>;;Default metric";
      }
    }
    container distance {
      tailf:info
        "Define an administrative distance";
      container bgp {
        tailf:info
          "BGP distance";
        tailf:cli-sequence-commands;
        tailf:cli-compact-syntax;
        leaf extern-as {
          tailf:cli-drop-node-name;
          tailf:cli-incomplete-command;
          type uint16 {
            tailf:info
              "<1-255>;;Distance for routes external to the AS";
            range "1..255";
          }
        }
        leaf internal-as {
          tailf:cli-drop-node-name;
          tailf:cli-incomplete-command;
          type uint16 {
            tailf:info
              "<1-255>;;Distance for routes internal to the AS";
            range "1..255";
          }
        }
        leaf local {
          tailf:cli-drop-node-name;
          type uint16 {
            tailf:info
              "<1-255>;;Distance for local routes";
            range "1..255";
          }
        }
      }
      list adm-distance {
        tailf:cli-drop-node-name;
        tailf:cli-suppress-mode;
        tailf:cli-delete-when-empty;
        key "distance srcip wildbits";
        leaf distance {
          type uint16 {
            tailf:info
              "<1-255>;;Administrative distance";
            range "1..255";
          }
        }
        leaf srcip {
          type inet:ipv4-address {
            tailf:info
              "A.B.C.D;;IP Source address";
          }
        }
        leaf wildbits {
          type inet:ipv4-address {
            tailf:info
              "A.B.C.D;;Wildcard bits";
          }
        }
        leaf acl {
          tailf:cli-drop-node-name;
          type union {
            type uint16 {
              range "1..99" {
                tailf:info
                  "<1-99>;;IP Standard access list number";
              }
            }
            type uint16 {
              range "1300..1999" {
                tailf:info
                  "<1300-1999>;;IP Standard expanded access list number";
              }
            }
            type string {
              pattern '[a-zA-Z].*';
              tailf:info
                "WORD;;Standard access-list name";
            }
          }
        }
      }
    }
    list distribute-list {
      tailf:info
        "Filter networks in routing updates";
      tailf:cli-compact-syntax;
      tailf:cli-suppress-mode;
      tailf:cli-delete-when-empty;
      key "id";
      leaf id {
        tailf:cli-incomplete-command;
        type ncs_rpc_notif_bgp-distribute-list-type;
      }
      choice in-out-choice {
        container in {
          presence "enable incoming routing updates";
          tailf:info
            "Filter incoming routing updates";
          leaf interface {
            type string;
          }
        }
        container out {
          presence "enable outgoing routing updates";
          tailf:info
            "Filter outgoing routing updates";
          leaf interface {
            type string;
          }
        }
      }
    }
    container maximum-paths {
      tailf:info
        "Forward packets over multiple paths";
      choice max-path-choice {
        case eibgp-case {
          container eibgp {
            tailf:info
              "Both eBGP and iBGP paths as multipath";
            uses ncs_rpc_notif_max-path-grouping;
          }
        }
        case ibgp-case {
          container ibgp {
            tailf:info
              "iBGP-multipath";
            choice ibgp-choice {
              case a {
                container unequal-cost {
                  tailf:info
                    "Perform Un-Equal cost multipath selection";
                  uses ncs_rpc_notif_max-path-grouping;
                }
              }
              case b {
                uses ncs_rpc_notif_max-path-grouping;
              }
            }
          }
        }
        case none-case {
          uses ncs_rpc_notif_max-path-grouping;
        }
        case import-case {
          leaf import {
            tailf:info
              "Maximum import paths";
            type uint16 {
              range "1..16";
              tailf:info
                "<1-16>;;Number of import paths";
            }
          }
        }
      }
    }
    list neighbor {
      tailf:info
        "Specify a neighbor router";
      tailf:cli-suppress-mode;
      tailf:cli-delete-when-empty;
      tailf:cli-incomplete-command;
      ordered-by user;
      must 'count(*) > 1' {
        tailf:xpath-root 3;
        tailf:dependency ".";
      }
      key "id";
      leaf id {
        type union {
          type string {
            tailf:info
              "WORD;;Neighbor tag";
          }
          type inet:ipv4-address {
            tailf:info
              "A.B.C.D;;Neighbor address";
          }
          type inet:ipv6-address {
            tailf:info
              "X:X:X:X::X;;Neighbor IPv6 address";
          }
        }
      }
      container peer-group {
        tailf:info
          "Member of the peer-group";
        tailf:cli-delete-when-empty;
        presence "true";
        leaf peer-group-name {
          tailf:info
            "WORD;;peer-group name";
          tailf:cli-drop-node-name;
          tailf:cli-delete-container-on-delete;
          tailf:cli-full-command;
          type string;
        }
      }
      leaf remote-as {
        tailf:info
          "Specify a BGP neighbor";
        tailf:cli-full-command;
        tailf:cli-delete-container-on-delete;
        type uint16 {
          tailf:info
            "<1-65535>  AS of remote neighbor";
          range "1..65535";
        }
      }
      container local-as {
        tailf:info
          "Specify a local-as number";
        tailf:cli-compact-syntax;
        tailf:cli-sequence-commands {
          tailf:cli-reset-siblings;
        }
        tailf:cli-delete-when-empty;
        presence "Specify a local-as number";
        leaf as-no {
          tailf:cli-drop-node-name;
          type uint16 {
            range "1..65535";
            tailf:info
              "<1-65535>;;AS number used as local AS";
          }
        }
        leaf no-prepend {
          tailf:info
            "Do not prepend local-as to updates from ebgp peers";
          type empty;
        }
        leaf replace-as {
          tailf:info
            "Replace real AS with local AS in the EBGP updates";
          type empty;
        }
        leaf dual-as {
          tailf:info
            "Accept either real AS or local AS from the ebgp peer";
          type empty;
        }
      }
      leaf activate {
        tailf:info
          "Enable the Address Family for this Neighbor";
        tailf:cli-full-command;
        type empty;
      }
      leaf advertisement-interval {
        tailf:info
          "Minimum interval between sending BGP routing updates";
        tailf:cli-full-command;
        type uint16 {
          range "0..600";
          tailf:info
            "<0-600>;;time in seconds";
        }
      }
      container allowas-in {
        tailf:info
          "Accept as-path with my AS present in it";
        presence "accept as-paths";
        tailf:cli-delete-when-empty;
        leaf as-number {
          tailf:cli-drop-node-name;
          type uint8 {
            range "1..10";
            tailf:info
              "<1-10>  Number of occurances of AS number";
          }
        }
      }
      container as-override {
        tailf:info
          "Override matching AS-number while sending update";
        tailf:cli-delete-when-empty;
        presence "true";
        leaf disable {
          type empty;
        }
      }
      container capability {
        tailf:info
          "Advertise capability to the peer";
        container orf {
          tailf:info
            "Advertise ORF capability to the peer";
          leaf-list prefix-list {
            tailf:cli-flat-list-syntax;
            tailf:info
              "Advertise prefixlist ORF capability to this neighbor";
            max-elements 1;
            type enumeration {
              enum "both" {
                tailf:info
                  "Capability to SEND and RECEIVE the ORF to/from this neighbor";
              }
              enum "receive" {
                tailf:info
                  "Capability to RECEIVE the ORF from this neighbor";
              }
              enum "send" {
                tailf:info
                  "Capability to SEND the ORF to this neighbor";
              }
            }
          }
        }
      }
      container default-originate {
        tailf:info
          "Originate default route to this neighbour";
        tailf:cli-delete-when-empty;
        presence "enable originate default route to this neighbour";
        leaf route-map {
          tailf:info
            "Route-map to specify criteria to originate default";
          type string {
            tailf:info
              "WORD;;route-map name";
          }
        }
      }
      leaf description {
        tailf:info
          "Neighbor specific description";
        tailf:cli-full-command;
        tailf:cli-multi-value;
        type string {
          tailf:info
            "LINE;;Up to 80 characters describing this neighbor";
        }
      }
      leaf disable-connected-check {
        tailf:info
          "One-hop away EBGP peer using loopback address";
        tailf:cli-full-command;
        type empty;
      }
      list distribute-list {
        tailf:info
          "Filter updates to/from this neighbor";
        tailf:cli-suppress-mode;
        tailf:cli-delete-when-empty;
        key "inout";
        leaf inout {
          type enumeration {
            enum "in" {
              tailf:code-name "dist_in";
              tailf:info
                "Filter incoming updates";
            }
            enum "out" {
              tailf:code-name "dist_out";
              tailf:info
                "Filter outgoing updates";
            }
          }
        }
        leaf accesslist {
          tailf:cli-drop-node-name;
          tailf:cli-prefix-key;
          type ncs_rpc_notif_bgp-distribute-list-type2;
          mandatory true;
        }
      }
      leaf dmzlink-bw {
        tailf:info
          "Propagate the DMZ link bandwidth";
        tailf:cli-full-command;
        type empty;
      }
      container ebgp-multihop {
        tailf:info
          "Allow EBGP neighbors not on directly connected networks";
        tailf:cli-delete-when-empty;
        presence "Allow EBGP neighbors not on directly connected networks";
        leaf max-hop {
          tailf:cli-drop-node-name;
          type uint8 {
            range "1..255";
            tailf:info
              "<1-255>;;maximum hop count";
          }
        }
      }
      leaf fall-over {
        tailf:info
          "session fall on peer route lost";
        tailf:cli-full-command;
        type empty;
      }
      list filter-list {
        tailf:info
          "Establish BGP filters";
        tailf:cli-suppress-mode;
        tailf:cli-delete-when-empty;
        key "inout";
        leaf inout {
          type enumeration {
            enum "in" {
              tailf:code-name "filter_in";
              tailf:info
                "Filter incoming routes";
            }
            enum "out" {
              tailf:code-name "filter_out";
              tailf:info
                "Filter outgoing routes";
            }
          }
        }
        leaf as-path-list {
          tailf:cli-drop-node-name;
          tailf:cli-prefix-key;
          type uint16 {
            range "1..500";
            tailf:info
              "<1-500>;;AS path access list";
          }
          mandatory true;
        }
      }
      container inherit {
        tailf:info
          "Inherit a template";
        leaf peer-policy {
          tailf:info
            "Inherit a peer-policy template";
          tailf:cli-full-command;
          type string {
            tailf:info
              "WORD;;Template name";
          }
        }
        leaf peer-session {
          tailf:info
            "Inherit a peer-session template";
          tailf:cli-full-command;
          type string {
            tailf:info
              "WORD;;Template name";
          }
        }
      }
      container maximum-prefix {
        tailf:info
          "Maximum number of prefixes accepted from this peer";
        tailf:cli-compact-syntax;
        tailf:cli-sequence-commands {
          tailf:cli-reset-all-siblings;
        }
        leaf max-prefix-no {
          tailf:cli-drop-node-name;
          type uint32 {
            range "1..2147483647";
            tailf:info
              "<1-2147483647>;;maximum no. of prefix limit";
          }
        }
        leaf threshold {
          tailf:cli-drop-node-name;
          tailf:cli-break-sequence-commands;
          type uint8 {
            range "1..100";
            tailf:info
              "<1-100>;;Threshold value (%) at which to generate a warning msg";
          }
        }
        leaf restart {
          tailf:cli-full-command;
          tailf:info
            "Restart bgp connection after limit is exceeded";
          type uint16 {
            range "1..65535";
            tailf:info
              "<1-65535>  Restart interval in minutes";
          }
        }
        leaf warning-only {
          tailf:cli-full-command;
          tailf:info
            "Only give warning message when limit is exceeded";
          type empty;
        }
      }
      leaf next-hop-self {
        tailf:cli-full-command;
        tailf:info
          "Disable the next hop calculation for this neighbor";
        type empty;
      }
      leaf next-hop-unchanged {
        tailf:cli-full-command;
        tailf:info
          "Propagate the iBGP paths's next hop unchanged for this neighbor";
        type empty;
      }
      container password {
        tailf:info
          "Set a password";
        tailf:cli-compact-syntax;
        leaf enctype {
          tailf:cli-drop-node-name;
          tailf:cli-incomplete-command;
          tailf:cli-reset-container;
          type uint8 {
            range "0..7";
            tailf:info
              "<0-7>;;Encryption type (0 to disable encryption, 7 for proprietary)";
          }
          default "0";
        }
        leaf text {
          tailf:cli-drop-node-name;
          tailf:cli-full-command;
          tailf:cli-multi-value;
          tailf:cli-reset-container;
          type string {
            tailf:info
              "LINE;;The password";
          }
        }
      }
      list prefix-list {
        tailf:info
          "Filter updates to/from this neighbor";
        tailf:cli-suppress-mode;
        tailf:cli-delete-when-empty;
        key "inout";
        leaf inout {
          type enumeration {
            enum "in" {
              tailf:code-name "prefix_in";
              tailf:info
                "Filter incoming updates";
            }
            enum "out" {
              tailf:code-name "prefix_out";
              tailf:info
                "Filter outgoing updates";
            }
          }
        }
        leaf prefix-list-name {
          tailf:cli-drop-node-name;
          tailf:cli-prefix-key;
          type string {
            tailf:info
              "WORD;;Name of a prefix list";
          }
          mandatory true;
        }
      }
      leaf remove-private-as {
        tailf:cli-full-command;
        tailf:info
          "Remove private AS number from outbound updates";
        type empty;
      }
      list route-map {
        tailf:info
          "Apply route map to neighbor";
        tailf:cli-suppress-mode;
        tailf:cli-delete-when-empty;
        key "inout";
        leaf inout {
          type enumeration {
            enum "in" {
              tailf:code-name "route_in";
              tailf:info
                "Apply map to incoming routes";
            }
            enum "out" {
              tailf:code-name "route_out";
              tailf:info
                "Apply map to outbound routes";
            }
          }
        }
        leaf route-map-name {
          tailf:cli-drop-node-name;
          tailf:cli-prefix-key;
          type string {
            tailf:info
              "WORD;;Name of route map";
          }
          mandatory true;
        }
      }
      leaf route-reflector-client {
        tailf:cli-full-command;
        tailf:info
          "Configure a neighbor as Route Reflector client";
        type empty;
      }
      container send-community {
        tailf:info
          "Send Community attribute to this neighbor";
        tailf:cli-delete-when-empty;
        presence "true";
        leaf send-community-where {
          tailf:cli-drop-node-name;
          type enumeration {
            enum "both" {
              tailf:info
                "Send Standard and Extended Community attributes";
            }
            enum "extended" {
              tailf:info
                "Send Extended Community attribute";
            }
            enum "standard" {
              tailf:code-name "send_standard";
              tailf:info
                "Send Standard Community attribute";
            }
          }
        }
      }
      container send-label {
        tailf:info
          "Send NLRI + MPLS Label to this peer";
        leaf send-label-explicit {
          tailf:cli-drop-node-name;
          type enumeration {
            enum "explicit-null" {
              tailf:code-name "send_explicit_null";
              tailf:info
                "Advertise Explicit Null label in place of Implicit Null";
            }
          }
        }
      }
      leaf shutdown {
        tailf:cli-full-command;
        tailf:info
          "Administratively shut down this neighbor";
        type empty;
      }
      leaf soft-reconfiguration {
        tailf:cli-full-command;
        tailf:info
          "Per neighbor soft reconfiguration";
        type enumeration {
          enum "inbound" {
            tailf:info
              "Allow inbound soft reconfiguration for this neighbor";
          }
        }
      }
      container timers {
        tailf:info
          "BGP per neighbor timers";
        tailf:cli-compact-syntax;
        tailf:cli-sequence-commands {
          tailf:cli-reset-siblings;
        }
        leaf keepalive-interval {
          tailf:cli-drop-node-name;
          tailf:cli-incomplete-command;
          type uint16 {
            range "0..65535";
            tailf:info
              "<0-65535>;;Keepalive interval";
          }
        }
        leaf holdtime {
          tailf:cli-drop-node-name;
          type uint16 {
            range "0..65535";
            tailf:info
              "<0-65535>;;Holdtime";
          }
        }
        leaf minimum-neighbor-hold {
          tailf:cli-drop-node-name;
          type uint16 {
            range "0..65535";
            tailf:info
              "<0-65535>  Minimum hold time from neighbor";
          }
        }
      }
      container translate-update {
        tailf:info
          "Translate Update to MBGP format";
        container ipv4 {
          tailf:info
            "Address Family";
          container multicast {
            tailf:info
              "Address Family modifier";
            tailf:cli-delete-when-empty;
            presence "Address Family modifier";
            leaf unicast {
              tailf:info
                "Address Family modifier";
              type empty;
            }
          }
        }
      }
      container transport {
        tailf:info
          "Transport options";
        leaf connection-mode {
          tailf:info
            "Specify passive or active connection";
          type enumeration {
            enum "active" {
              tailf:info
                "Actively establish the TCP session";
            }
            enum "passive" {
              tailf:info
                "Passively establish the TCP session";
            }
          }
        }
      }
      container ttl-security {
        tailf:info
          "BGP ttl security check";
        leaf hops {
          tailf:info
            "IP hops";
          type uint8 {
            range "1..254";
            tailf:info
              "<1-254>;;maximum number of hops";
          }
        }
      }
      leaf unsuppress-map {
        tailf:info
          "Route-map to selectively unsuppress suppressed routes";
        tailf:cli-full-command;
        type string {
          tailf:info
            "WORD;;Name of route map";
        }
      }
      container update-source {
        tailf:info
          "Source of routing updates";
        tailf:cli-diff-dependency "/ios:interface" {
          tailf:xpath-root 3;
        }
        uses ncs_rpc_notif_interface-grouping;
      }
      leaf version {
        tailf:cli-full-command;
        tailf:info
          "Set the BGP version to match a neighbor";
        type uint16 {
          range "4";
          tailf:info
            "<4-4>;;Neighbor's BGP version";
        }
      }
      leaf weight {
        tailf:cli-full-command;
        tailf:info
          "Set default weight for routes from this neighbor";
        type uint16 {
          range "0..65535";
          tailf:info
            "<0-65535>;;default weight";
        }
      }
      container ha-mode {
        tailf:info
          "high availability mode";
        container graceful-restart {
          tailf:info
            "graceful-restart for this peer";
          presence "true";
          leaf disable {
            tailf:info
              "disable graceful-restart";
            type empty;
          }
        }
        container sso {
          tailf:info
            "stateful-switchover support for this peer";
          presence "true";
          leaf disable {
            tailf:info
              "disable stateful-switchover";
            type empty;
          }
        }
      }
    }
    list network {
      tailf:info
        "Specify a network to announce via BGP";
      tailf:cli-suppress-mode;
      tailf:cli-delete-when-empty;
      tailf:cli-compact-syntax;
      tailf:cli-reset-container;
      key "number";
      leaf number {
        type inet:ipv4-address {
          tailf:info
            "A.B.C.D;;Network number";
        }
      }
      leaf backdoor {
        tailf:info
          "Specify a BGP backdoor route";
        tailf:cli-full-command;
        type empty;
      }
      leaf mask {
        tailf:info
          "Network mask";
        type inet:ipv4-address {
          tailf:info
            "A.B.C.D;;Network mask";
        }
      }
      leaf route-map {
        tailf:info
          "Route-map to modify the attributes";
        type string {
          tailf:info
            "WORD;;Name of the route map";
        }
      }
    }
    container redistribute {
      tailf:info
        "Redistribute information from another routing protocol";
      container bgp {
        tailf:info
          "Border Gateway Protocol (BGP)";
        tailf:cli-compact-syntax;
        tailf:cli-sequence-commands {
          tailf:cli-reset-all-siblings;
        }
        leaf as-no {
          tailf:cli-drop-node-name;
          type uint16 {
            range "1..65535";
            tailf:info
              "<1-65535>;;Autonomous system number";
          }
        }
        uses ncs_rpc_notif_metric-route-map-grouping;
      }
      container connected {
        tailf:info
          "Connected";
        tailf:cli-delete-when-empty;
        presence "Connected";
        uses ncs_rpc_notif_metric-route-map-grouping;
      }
      container dvmrp {
        tailf:info
          "Redistribution of DVMRP into BGP IPv4 Multicast";
        tailf:cli-compact-syntax;
        tailf:cli-sequence-commands {
          tailf:cli-reset-siblings;
        }
        tailf:cli-delete-when-empty;
        presence "Redistribution of DVMRP into BGP IPv4 Multicast";
        uses ncs_rpc_notif_route-map-metric-grouping;
      }
      container eigrp {
        tailf:info
          "Enhanced Interior Gateway Routing Protocol (EIGRP)";
        tailf:cli-compact-syntax;
        tailf:cli-sequence-commands {
          tailf:cli-reset-all-siblings;
        }
        leaf as-no {
          tailf:cli-drop-node-name;
          type uint16 {
            range "1..65535";
            tailf:info
              "<1-65535>;;Autonomous system number";
          }
        }
        uses ncs_rpc_notif_metric-route-map-grouping;
      }
      container isis {
        tailf:info
          "ISO IS-IS";
        list isis-area {
          tailf:cli-drop-node-name;
          key "name";
          leaf name {
            type string {
              tailf:info
                "WORD;;ISO routing area tag";
              pattern '^([^mlir].*)|(i[^p].*)|(ip..*)|(l[^e].*)|(le[^v].*)|(lev[^e].*)|(leve[^l].*)|(level[^\-].*)|(m[^e].*)|(me[^t].*)|(met[^r].*)|(metr[^i].*)|(metri[^c].*)|(metric..*)*(r[^o].*)|(ro[^u].*)|(rou[^t].*)|(rout[^e].*)|(route[^\-].*)|(route-[^m].*)|(route-m[^a].*)|(route-ma[^p].*)|(route-map..*)$';
            }
          }
          uses ncs_rpc_notif_redistribute-isis-grouping;
        }
        container default {
          tailf:cli-drop-node-name;
          uses ncs_rpc_notif_redistribute-isis-grouping;
        }
      }
      container iso-igrp {
        tailf:info
          "IGRP for OSI networks";
        list iso-igrp-area {
          tailf:cli-compact-syntax;
          tailf:cli-sequence-commands;
          tailf:cli-drop-node-name;
          key "name";
          leaf name {
            type string {
              tailf:info
                "WORD;;Pointer to route-map entries";
              pattern '^([^r].*)|(r^[o].*)|(ro[^u].*)|(rou[^t].*)|(rout[^e].*)|(route[^\-].*)|(route-[^m].*)|(route-m[^a].*)|(route-ma[^p])|(route-map..*)';
            }
          }
          uses ncs_rpc_notif_route-map-metric-grouping;
        }
        container default {
          tailf:cli-compact-syntax;
          tailf:cli-sequence-commands;
          uses ncs_rpc_notif_route-map-metric-grouping;
        }
      }
      container mobile {
        presence "Mobile routes";
        tailf:info
          "Mobile routes";
        uses ncs_rpc_notif_metric-route-map-grouping;
      }
      container odr {
        presence "On Demand stub Routes";
        tailf:info
          "On Demand stub Routes";
        uses ncs_rpc_notif_metric-route-map-grouping;
      }
      list ospf {
        tailf:info
          "Open Shortest Path First (OSPF)";
        key "id";
        leaf id {
          type uint16 {
            range "1..65535";
            tailf:info
              "<1-65535>;;Process ID";
          }
        }
        list vrf {
          tailf:info
            "VPN Routing/Forwarding Instance";
          tailf:cli-diff-dependency "/ios:ip/vrf" {
            tailf:xpath-root 3;
          }
          tailf:cli-diff-dependency "/ios:vrf/definition" {
            tailf:xpath-root 3;
          }
          key "name";
          leaf name {
            type string {
              tailf:info
                "WORD;;VPN Routing/Forwarding Instance (VRF) name";
            }
          }
          container match {
            tailf:info
              "Redistribution of OSPF routes";
          }
          uses ncs_rpc_notif_metric-route-map-grouping;
        }
        container non-vrf {
          tailf:cli-drop-node-name;
          container match {
            tailf:info
              "Redistribution of OSPF routes";
          }
          uses ncs_rpc_notif_metric-route-map-grouping;
        }
      }
      container rip {
        presence "Routing Information Protocol (RIP)";
        tailf:info
          "Routing Information Protocol (RIP)";
        uses ncs_rpc_notif_metric-route-map-grouping;
      }
      container static {
        presence "Static routes";
        tailf:info
          "Static routes";
        uses ncs_rpc_notif_metric-route-map-grouping;
      }
    }
    leaf synchronization {
      tailf:info
        "Perform IGP synchronization";
      tailf:cli-full-command;
      type empty;
    }
    leaf auto-summary {
      tailf:info
        "Enable automatic network number summarization";
      tailf:cli-boolean-no;
      tailf:cli-trim-default;
      tailf:cli-full-command;
      type boolean;
      default "false";
    }
    leaf table-map {
      tailf:info
        "Map external entry attributes into routing table";
      tailf:cli-full-command;
      type string {
        tailf:info
          "WORD;;route-map name";
      }
    }
    container timers {
      tailf:info
        "Adjust routing timers";
      tailf:cli-compact-syntax;
      tailf:cli-sequence-commands {
        tailf:cli-reset-siblings;
      }
      leaf keepalive-interval {
        tailf:cli-drop-node-name;
        tailf:cli-incomplete-command;
        type uint16 {
          range "0..65535";
          tailf:info
            "<0-65535>;;Keepalive interval";
        }
      }
      leaf holdtime {
        tailf:cli-drop-node-name;
        type uint16 {
          range "0..65535";
          tailf:info
            "<0-65535>;;Holdtime";
        }
      }
      leaf minimum-neighbor-hold {
        tailf:cli-drop-node-name;
        type uint16 {
          range "0..65535";
          tailf:info
            "<0-65535>  Minimum hold time from neighbor";
        }
      }
    }
  }

  grouping ncs_rpc_notif_ospf-ospfv3-common-address-family-grouping {
    container default-information {
      tailf:info
        "Control distribution of default information";
      container originate {
        tailf:info
          "Distribute a default route";
        presence "Distribute a default route";
        leaf always {
          tailf:info
            "Always advertise default route";
          type empty;
        }
        leaf metric {
          tailf:info
            "OSPF default metric";
          type uint32 {
            range "0 .. 16777214";
            tailf:info
              "<0-16777214>;;OSPF metric";
          }
          tailf:cli-no-value-on-delete;
        }
        leaf metric-type {
          tailf:info
            "OSPF metric type for default routes";
          type ncs_rpc_notif_ospf-metric-type;
          tailf:cli-no-value-on-delete;
        }
        leaf route-map {
          tailf:info
            "Route map reference";
          type string {
            tailf:info
              "WORD;;Route map name";
          }
          tailf:cli-no-value-on-delete;
        }
      }
    }
    leaf default-metric {
      tailf:info
        "Set metric of redistributed routes";
      tailf:cli-full-command;
      type uint32 {
        range "1 .. 16777214";
        tailf:info
          "<1-16777214>;;OSPF default metric";
      }
    }
    container discard-route {
      tailf:info
        "Enable or disable discard-route installation";
      presence "Enable or disable discard-route installation";
      tailf:cli-compact-syntax;
      leaf external {
        tailf:info
          "Discard route for redistributed summarised routes";
        type uint32 {
          range "1 .. 255";
          tailf:info
            "<1-255>;;Administrative distance for redistributed summarised routes";
        }
      }
      leaf internal {
        tailf:info
          "Discard route for summarised internal routes";
        type uint32 {
          range "1 .. 255";
          tailf:info
            "<1-255>;;Administrative distance for summarised internal routes";
        }
      }
    }
    container distance {
      tailf:cli-compact-syntax;
      tailf:info
        "Define an administrative distance";
      container ospf-distance {
        tailf:cli-compact-syntax;
        tailf:cli-drop-node-name;
        leaf distance {
          tailf:cli-drop-node-name;
          type uint32 {
            range "1 .. 255";
            tailf:info
              "<1-255>;;OSPF Administrative distance";
          }
        }
        tailf:cli-sequence-commands;
        leaf ip {
          tailf:cli-drop-node-name;
          tailf:cli-incomplete-command;
          type inet:ipv4-address {
            tailf:info
              "A.B.C.D;;IP source address";
          }
        }
        leaf wildcard {
          tailf:cli-drop-node-name;
          type inet:ipv4-address {
            tailf:info
              "A.B.C.D;;Wildcard bits";
          }
        }
        leaf acl-name {
          tailf:cli-drop-node-name;
          type ncs_rpc_notif_access-list-standard-id-type;
          tailf:cli-no-value-on-delete;
        }
      }
      container ospf {
        tailf:info
          "OSPF routes Administrative distance";
        leaf external {
          tailf:info
            "External routes";
          type uint32 {
            range "1 .. 255";
            tailf:info
              "<1-255>;;Distance for external routes";
          }
          tailf:cli-suppress-no;
          tailf:cli-no-value-on-delete;
          tailf:cli-no-name-on-delete;
        }
        leaf inter-area {
          tailf:info
            "Inter-area routes";
          type uint32 {
            range "1 .. 255";
            tailf:info
              "<1-255>;;Distance for inter-area routes";
          }
          tailf:cli-suppress-no;
          tailf:cli-no-name-on-delete;
          tailf:cli-no-value-on-delete;
        }
        leaf intra-area {
          tailf:info
            "Intra-area routes";
          type uint32 {
            range "1 .. 255";
            tailf:info
              "<1-255>;;Distance for intra-area routes";
          }
          tailf:cli-suppress-no;
          tailf:cli-no-name-on-delete;
          tailf:cli-no-value-on-delete;
        }
      }
    }
    leaf maximum-paths {
      tailf:info
        "Forward packets over multiple paths";
      tailf:cli-full-command;
      type uint32 {
        range "1 .. 32";
        tailf:info
          "<1-32>;;Number of paths";
      }
    }
    container redistribute {
      tailf:info
        "Redistribute information from another routing protocol";
      uses ncs_rpc_notif_ospf-redistribute-grouping;
      container bgp {
        tailf:info
          "Border Gateway Protocol (BGP)";
        tailf:cli-sequence-commands;
        uses ncs_rpc_notif_ospf-redistribute-bgp-grouping;
      }
      container connected {
        tailf:info
          "Connected";
        presence "Connected";
        uses ncs_rpc_notif_ospf-redistribute-grouping;
      }
      container eigrp {
        tailf:info
          "Enhanced Interior Gateway Routing Protocol (EIGRP)";
        tailf:cli-sequence-commands;
        uses ncs_rpc_notif_ospf-redistribute-bgp-grouping;
      }
      container isis {
        presence "ISO IS-IS";
        tailf:info
          "ISO IS-IS";
        choice isis-level-routes-isis-area-choice {
          leaf isis-level-routes {
            tailf:cli-drop-node-name;
            type enumeration {
              enum "level-1" {
                tailf:info
                  "IS-IS level-1 routes only";
              }
              enum "level-2" {
                tailf:info
                  "IS-IS level-2 routes only";
              }
              enum "level-1-2" {
                tailf:info
                  "IS-IS level-1 and level-2 routes";
              }
            }
          }
          list isis-area {
            tailf:cli-suppress-mode;
            tailf:cli-delete-when-empty;
            tailf:cli-drop-node-name;
            key "name";
            leaf name {
              tailf:cli-disallow-value "level-1|level-2|level-1-2|metric|metric-type|route-map|subnets|tag";
              type string {
                tailf:info
                  "WORD;;ISO routing area tag";
              }
            }
            uses ncs_rpc_notif_ospf-redistribute-grouping;
          }
        }
        uses ncs_rpc_notif_ospf-redistribute-grouping;
      }
      container iso-igrp {
        tailf:info
          "IGRP for OSI networks";
        presence "IGRP for OSI networks";
        tailf:cli-sequence-commands;
        choice area-tag-route-map-choice {
          container area-tag-route-map-container {
            tailf:cli-drop-node-name;
            tailf:cli-flatten-container;
            tailf:cli-sequence-commands;
            leaf area-tag {
              tailf:cli-drop-node-name;
              tailf:cli-disallow-value "route-map";
              type string {
                tailf:info
                  "WORD;;ISO routing area tag";
              }
            }
            leaf route-map {
              tailf:info
                "Route map reference";
              type string {
                tailf:info
                  "WORD;;Pointer to route-map entries";
              }
            }
          }
          leaf route-map {
            tailf:info
              "Route map reference";
            type string {
              tailf:info
                "WORD;;Pointer to route-map entries";
            }
          }
        }
        container iso-igrp-container {
          tailf:cli-drop-node-name;
          tailf:cli-compact-syntax;
          uses ncs_rpc_notif_ospf-iso-igrp-redistribute-grouping;
        }
      }
      container maximum-prefix {
        tailf:info
          "Maximum number of prefixes redistributed to protocol";
        tailf:cli-sequence-commands;
        tailf:cli-compact-syntax;
        leaf number {
          tailf:cli-drop-node-name;
          type uint32 {
            range "1 .. 4294967295";
            tailf:info
              "<1-4294967295>;;Maximum number of IP prefixes redistributed";
          }
        }
        container threshold-warning-only-container {
          tailf:cli-compact-syntax;
          tailf:cli-drop-node-name;
          leaf threshold {
            tailf:cli-drop-node-name;
            type uint32 {
              range "1 .. 100";
              tailf:info
                "<1-100>;;Threshold value (%) at which to generate a warning message";
            }
          }
          leaf warning-only {
            tailf:info
              "Only give warning message when limit is exceeded";
            tailf:cli-full-command;
            type empty;
          }
        }
      }
      container mobile {
        tailf:info
          "Mobile routes";
        presence "Mobile routes";
        uses ncs_rpc_notif_ospf-redistribute-grouping;
      }
      container odr {
        tailf:info
          "On Demand stub Routes";
        presence "On Demand stub Routes";
        uses ncs_rpc_notif_ospf-redistribute-grouping;
      }
      list ospf {
        tailf:info
          "Open Shortest Path First (OSPF)";
        tailf:cli-suppress-mode;
        tailf:cli-delete-when-empty;
        key "id";
        leaf id {
          tailf:cli-suppress-range;
          type uint32 {
            range "1 .. 65535";
            tailf:info
              "<1-65535>;;Process ID";
          }
        }
        container match {
          tailf:cli-compact-syntax;
          tailf:cli-flatten-container;
          tailf:info
            "Redistribution of OSPF routes";
          container internal {
            presence "Redistribute OSPF internal routes";
            tailf:info
              "Redistribute OSPF internal routes";
            tailf:cli-compact-syntax;
            tailf:cli-flatten-container;
            uses ncs_rpc_notif_ospf-redistribute-match-grouping;
          }
          container external {
            tailf:info
              "Redistribute OSPF external routes";
            presence "Redistribute OSPF external routes";
            tailf:cli-compact-syntax;
            tailf:cli-flatten-container;
            leaf external-routes {
              tailf:cli-drop-node-name;
              type ncs_rpc_notif_redist-ospf-external-type;
            }
            uses ncs_rpc_notif_ospf-redistribute-match-grouping;
          }
          container nssa-external {
            tailf:info
              "Redistribute OSPF NSSA external routes";
            presence "Redistribute OSPF NSSA external routes";
            tailf:cli-compact-syntax;
            tailf:cli-flatten-container;
            leaf nssa-external-routes {
              tailf:cli-drop-node-name;
              type ncs_rpc_notif_redist-ospf-external-type;
            }
            uses ncs_rpc_notif_ospf-redistribute-match-grouping;
          }
        }
        uses ncs_rpc_notif_ospf-redistribute-grouping;
        leaf vrf {
          tailf:info
            "VPN Routing/Forwarding Instance";
          tailf:cli-diff-dependency "/ios:ip/vrf" {
            tailf:xpath-root 3;
          }
          tailf:cli-diff-dependency "/ios:vrf/definition" {
            tailf:xpath-root 3;
          }
          type string {
            tailf:info
              "WORD;;VPN Routing/Forwarding Instance (VRF) name";
          }
        }
      }
      container rip {
        tailf:info
          "Routing Information Protocol (RIP)";
        presence "Routing Information Protocol (RIP)";
        uses ncs_rpc_notif_ospf-redistribute-grouping;
      }
      container static {
        tailf:info
          "Static routes";
        presence "Static routes";
        uses ncs_rpc_notif_ospf-redistribute-grouping;
      }
    }
  }

  grouping ncs_rpc_notif_ospf-ospfv3-common-grouping {
    list area {
      tailf:info
        "OSPF area parameters";
      tailf:cli-suppress-mode;
      tailf:cli-delete-when-empty;
      tailf:cli-incomplete-command;
      key "id";
      leaf id {
        tailf:cli-suppress-range;
        type ncs_rpc_notif_ospf-area-type;
      }
      container authentication {
        tailf:info
          "Enable authentication";
        presence "true";
        leaf message-digest {
          tailf:info
            "Use message-digest authentication";
          type empty;
        }
      }
      leaf default-cost {
        tailf:info
          "Set the summary default-cost of a NSSA/stub area";
        tailf:cli-full-command;
        tailf:cli-no-value-on-delete;
        type uint32 {
          range "0 .. 16777215";
          tailf:info
            "<0-16777215;;Stub's advertised external route metric";
        }
      }
      list filter-list {
        tailf:info
          "Filter networks between OSPF areas";
        tailf:cli-suppress-mode;
        tailf:cli-delete-when-empty;
        tailf:cli-compact-syntax;
        key "in-out";
        leaf prefix {
          tailf:cli-prefix-key;
          mandatory true;
          tailf:info
            "Filter prefixes between OSPF areas";
          type string {
            tailf:info
              "WORD;;Name of an IP prefix-list";
          }
        }
        leaf in-out {
          type enumeration {
            enum "in" {
              tailf:info
                "Filter networks sent to this area";
            }
            enum "out" {
              tailf:info
                "Filter networks sent from this area";
            }
          }
        }
      }
      container nssa {
        tailf:info
          "Specify a NSSA area";
        presence "Specify a NSSA area";
        container default-information-originate {
          tailf:cli-flatten-container;
          tailf:info
            "Originate Type 7 default into NSSA area";
          presence "Originate Type 7 default into NSSA area";
          leaf metric {
            tailf:info
              "OSPF default metric";
            type int32 {
              range "0 .. 16777214";
              tailf:info
                "<0-16777214>;;OSPF metric";
            }
            tailf:cli-no-value-on-delete;
            tailf:cli-no-name-on-delete;
            tailf:cli-suppress-no;
          }
          leaf metric-type {
            tailf:info
              "OSPF metric type for default routes";
            type ncs_rpc_notif_ospf-metric-type;
          }
        }
        leaf no-ext-capability {
          tailf:info
            "Do not send domain specific capabilities into NSSA";
          type empty;
        }
        leaf no-redistribution {
          tailf:info
            "No redistribution into this NSSA area";
          type empty;
        }
        leaf no-summary {
          tailf:info
            "Do not send summary LSA into NSSA";
          type empty;
        }
        container translate {
          tailf:info
            "Translate LSA";
          container type7 {
            tailf:info
              "From Type 7 to Type 5";
            leaf suppress-fa {
              tailf:info
                "Suppress forwarding address in translated LSAs";
              type empty;
            }
          }
        }
      }
      list range {
        tailf:info
          "Summarize routes matching address/mask (border routers only)";
        tailf:cli-suppress-mode;
        tailf:cli-delete-when-empty;
        key "ip mask";
        leaf ip {
          type inet:ipv4-address {
            tailf:info
              "A.B.C.D;;IP address to match";
          }
        }
        leaf mask {
          type inet:ipv4-address {
            tailf:info
              "A.B.C.D;;IP mask for address";
          }
        }
        choice advertise-choice {
          leaf advertise {
            tailf:info
              "Advertise this range (default)";
            type empty;
          }
          leaf not-advertise {
            tailf:info
              "DoNotAdvertise this range";
            type empty;
          }
        }
        leaf cost {
          tailf:info
            "User specified metric for this range";
          tailf:cli-full-command;
          type uint32 {
            range "0 .. 16777215";
            tailf:info
              "<0-16777215>;;Advertised metric for this range";
          }
        }
      }
      list sham-link {
        tailf:info
          "Define a sham link and its parameters";
        tailf:cli-suppress-mode;
        tailf:cli-delete-when-empty;
        key "source dest";
        leaf source {
          type inet:ipv4-address {
            tailf:info
              "A.B.C.D;;IP addr associated with sham-link source";
          }
        }
        leaf dest {
          type inet:ipv4-address {
            tailf:info
              "A.B.C.D;;IP addr associated with sham-link destination";
          }
        }
        leaf cost {
          tailf:info
            "Associate a cost with the sham-link";
          type uint16 {
            range "0 .. 65535";
            tailf:info
              "<1-65535>;;Cost of the sham-link";
          }
        }
      }
      container stub {
        tailf:info
          "Specify a stub area";
        presence "Specify a stub area";
        leaf no-ext-capability {
          tailf:info
            "Do not send domain specific capabilities into stub area";
          type empty;
        }
        leaf no-summary {
          tailf:info
            "Do not send summary LSA into stub area";
          tailf:cli-full-command;
          type empty;
        }
      }
      list virtual-link {
        tailf:info
          "Define a virtual link and its parameters";
        tailf:cli-suppress-mode;
        tailf:cli-delete-when-empty;
        key "id";
        leaf id {
          type inet:ipv4-address {
            tailf:info
              "A.B.C.D;;ID (IP addr) associated with virtual link neighbor";
          }
        }
        leaf authentication {
          tailf:info
            "Set authentication type";
          type empty;
        }
        container authentication-key {
          tailf:info
            "Set authentication key";
          leaf auth-type {
            tailf:cli-drop-node-name;
            type uint8 {
              range "0 .. 7";
              tailf:info
                "<0-7>;;Encryption type (0 for not yet encrypted, 7 for proprietary)";
            }
          }
          leaf auth-key {
            tailf:cli-drop-node-name;
            tailf:cli-full-command;
            type string {
              length "1 .. 8";
              tailf:info
                "WORD;;Authentication key (8 chars)";
            }
          }
        }
        leaf dead-interval {
          tailf:info
            "Dead router detection time";
          tailf:cli-no-value-on-delete;
          type uint16 {
            range "1 .. 8192";
            tailf:info
              "<1-8192;;Seconds>";
          }
        }
        leaf hello-interval {
          tailf:info
            "Hello packet interval";
          tailf:cli-no-value-on-delete;
          type int32 {
            range "1 .. 8192";
            tailf:info
              "<1-8192;;Seconds>";
          }
        }
        list message-digest-key {
          tailf:info
            "Set message digest key";
          tailf:cli-suppress-mode;
          tailf:cli-delete-when-empty;
          tailf:cli-incomplete-command;
          key "id";
          leaf id {
            tailf:cli-suppress-range;
            type uint8 {
              range "1 .. 255";
              tailf:info
                "<1-255>;;Key ID";
            }
          }
          container md5 {
            tailf:info
              "Use MD5 algorithm";
            tailf:cli-sequence-commands;
            leaf auth-type {
              tailf:cli-drop-node-name;
              tailf:cli-optional-in-sequence;
              type uint8 {
                range "0 .. 7";
                tailf:info
                  "<0-7>;;Encryption type (0 for not yet encrypted, 7 for proprietary)";
              }
            }
            leaf auth-key {
              tailf:cli-drop-node-name;
              type string {
                length "1 .. 16";
                tailf:info
                  "WORD;;Authentication key (16 chars)";
              }
            }
          }
        }
        leaf retransmit-interval {
          tailf:info
            "LSA retransmit interval";
          type uint16 {
            range "1 .. 8192";
            tailf:info
              "<1-8192>;;Seconds";
          }
          tailf:cli-no-value-on-delete;
        }
        leaf transmit-delay {
          tailf:info
            "LSA transmission delay";
          type uint16 {
            range "1 .. 8192";
            tailf:info
              "<1-8192>;;Seconds";
          }
          tailf:cli-no-value-on-delete;
        }
      }
    }
    container auto-cost {
      tailf:info
        "Calculate OSPF interface cost according to bandwidth";
      presence "Calculate OSPF interface cost according to bandwidth";
      leaf reference-bandwidth {
        tailf:info
          "Use reference bandwidth method to assign OSPF cost";
        type uint32 {
          tailf:info
            "<1-4294967>;;The reference bandwidth in terms of Mbits per second";
          range "1 .. 4294967";
        }
      }
    }
    container bfd {
      tailf:info
        "BFD configuration commands";
      leaf all-interfaces {
        tailf:info
          "Enable BFD on all interfaces";
        type empty;
      }
    }
    container interface-id {
      tailf:info
        "Source of the interface ID";
      leaf snmp-if-index {
        tailf:info
          "SNMP MIB ifIndex";
        type empty;
      }
    }
    container log-adjacency-changes {
      tailf:info
        "Log changes in adjacency state";
      presence "true";
      leaf detail {
        tailf:info
          "Log all state changes";
        type empty;
      }
    }
    container max-lsa {
      tailf:info
        "maximum number of LSAs OSPF process will receive";
      tailf:cli-sequence-commands;
      leaf number {
        tailf:cli-drop-node-name;
        type uint32 {
          range "1 .. 4294967294";
          tailf:info
            "<1-4294967294>;;Maximum number of non self-generated LSAs this process can receive";
        }
      }
      container options {
        tailf:cli-drop-node-name;
        tailf:cli-compact-syntax;
        leaf threshold-value {
          tailf:cli-drop-node-name;
          type uint32 {
            range "1 .. 100";
            tailf:info
              "<1-100>;;Threshold value (%) at which to generate a warning msg";
          }
        }
        leaf ignore-count {
          tailf:info
            "maximum number of times adjacencies can be suppressed";
          type uint32 {
            range "1 .. 65534";
            tailf:info
              "<1-65534>;;count on how many times adjacencies can be suppressed";
          }
        }
        leaf ignore-time {
          tailf:info
            "time during which all adjacencies are suppressed";
          type uint32 {
            range "1 .. 17895";
            tailf:info
              "<1-17895>;;number of minutes during which all adjacencies are suppressed";
          }
        }
        leaf reset-time {
          tailf:info
            "time after which ignore-count is reset to zero";
          type uint32 {
            range "2 .. 35791";
            tailf:info
              "<2-35791>;;number of minutes after which ignore-count is reset to zero";
          }
        }
        leaf warning-only {
          tailf:info
            "Only give warning message when limit is exceeded";
          tailf:cli-full-command;
          type empty;
        }
      }
    }
    uses ncs_rpc_notif_passive-interface-grouping;
    container queue-depth {
      tailf:info
        "OSPF Hello/Router process queue depth";
      container hello {
        tailf:info
          "OSPF Hello process queue depth";
        uses ncs_rpc_notif_queue-depth-grouping;
      }
      container update {
        tailf:info
          "OSPF Router process queue depth";
        uses ncs_rpc_notif_queue-depth-grouping;
      }
    }
    container timers {
      tailf:info
        "Adjust routing timers";
      container lsa {
        tailf:info
          "OSPF LSA timers";
        leaf arrival {
          tailf:info
            "OSPF LSA arrival timer";
          type uint32 {
            range "0 .. 600000";
            tailf:info
              "<0-600000>;;The minimum interval in milliseconds between accepting the same LSA";
          }
        }
      }
      container pacing {
        tailf:info
          "OSPF pacing timers";
        leaf flood {
          tailf:info
            "OSPF flood pacing timer";
          tailf:cli-full-command;
          type uint32 {
            range "5 .. 100";
            tailf:info
              "<5-100>;;The minimum interval in msec to pace limit flooding on interface";
          }
        }
        leaf lsa-group {
          tailf:info
            "OSPF LSA group pacing timer";
          tailf:cli-full-command;
          type uint32 {
            range "10 .. 1800";
            tailf:info
              "<10-1800>;;Interval in sec between group of LSA being refreshed or maxaged";
          }
        }
        leaf retransmission {
          tailf:info
            "OSPF retransmission pacing timer";
          tailf:cli-full-command;
          type uint32 {
            range "5 .. 200";
            tailf:info
              "<5-200>;;The minimum interval in msec between neighbor retransmissions";
          }
        }
      }
      container throttle {
        tailf:info
          "OSPF throttle timers";
        container lsa {
          tailf:info
            "OSPF LSA throttle timers";
          container all {
            tailf:info
              "For all type of OSPF LSAs";
            tailf:cli-sequence-commands;
            tailf:cli-compact-syntax;
            leaf delay {
              tailf:cli-drop-node-name;
              tailf:cli-incomplete-command;
              type uint32 {
                range "0 .. 600000";
                tailf:info
                  "<0-600000>;;Delay to generate first occurrence of LSA in milliseconds";
              }
            }
            leaf min-delay {
              tailf:cli-drop-node-name;
              tailf:cli-incomplete-command;
              type uint32 {
                range "0 .. 600000";
                tailf:info
                  "<0-600000>;;Minimum delay between originating the same LSA in milliseconds";
              }
            }
            leaf max-delay {
              tailf:cli-drop-node-name;
              type uint32 {
                range "0 .. 600000";
                tailf:info
                  "<0-600000>;;Maximum delay between originating the same LSA in milliseconds";
              }
            }
          }
        }
        container spf {
          tailf:info
            "OSPF SPF throttle timers";
          tailf:cli-sequence-commands;
          tailf:cli-compact-syntax;
          leaf delay {
            tailf:cli-drop-node-name;
            tailf:cli-incomplete-command;
            type uint32 {
              range "0 .. 600000";
              tailf:info
                "<0-600000>;;Delay between receiving a change to SPF calculation in milliseconds";
            }
          }
          leaf min-delay {
            tailf:cli-drop-node-name;
            tailf:cli-incomplete-command;
            type uint32 {
              range "0 .. 600000";
              tailf:info
                "<0-600000>;;Delay between first and second SPF calculation in milliseconds";
            }
          }
          leaf max-delay {
            tailf:cli-drop-node-name;
            type uint32 {
              range "0 .. 600000";
              tailf:info
                "<0-600000>;;Maximum wait time in milliseconds for SPF calculations";
            }
          }
        }
      }
    }
    leaf router-id {
      tailf:cli-full-command;
      tailf:info
        "Override configured router identifier (peers will reset)";
      type inet:ipv4-address {
        tailf:info
          "A.B.C.D;;Manually configured router identifier";
      }
    }
  }

  grouping ncs_rpc_notif_ospfv3-address-family-grouping;

  grouping ncs_rpc_notif_queue-depth-grouping {
    leaf options {
      tailf:cli-drop-node-name;
      tailf:cli-full-command;
      tailf:cli-trim-default;
      type union {
        type uint32 {
          range "1 .. 2147483647";
          tailf:info
            "<1-2147483647>;;maximum numer of packets in the queue";
        }
        type enumeration {
          enum "unlimited" {
            tailf:info
              "Unlimited queue depth";
          }
        }
      }
      default "unlimited";
    }
  }

  grouping ncs_rpc_notif_ospf-redistribute-match-grouping {
    leaf metric {
      tailf:info
        "Metric for redistributed routes";
      type uint32 {
        tailf:info
          "<0-16777214>;;OSPF default metric";
      }
    }
    leaf subnets {
      tailf:info
        "Consider subnets for redistribution into OSPF";
      type empty;
    }
    leaf route-map {
      tailf:info
        "Route map reference";
      type string {
        tailf:info
          "WORD;;Pointer to route-map entries";
      }
    }
    leaf tag {
      tailf:info
        "Set tag for routes redistributed into OSPF";
      type uint32 {
        range "0 .. 4294967295";
        tailf:info
          "<0-4294967295>;;32-bit tag value";
      }
    }
  }

  grouping ncs_rpc_notif_ospf-iso-igrp-redistribute-grouping {
    leaf metric {
      tailf:info
        "Metric for redistributed routes";
      type uint32 {
        tailf:info
          "<0-16777214>;;OSPF default metric";
      }
    }
    leaf metric-type {
      tailf:info
        "OSPF/IS-IS exterior metric type for redistributed routes";
      type enumeration {
        enum "1" {
          tailf:info
            "Set OSPF External Type 1 metrics";
        }
        enum "2" {
          tailf:info
            "Set OSPF External Type 2 metrics";
        }
      }
    }
    leaf tag {
      tailf:info
        "Set tag for routes redistributed into OSPF";
      type uint32 {
        range "0 .. 4294967295";
        tailf:info
          "<0-4294967295>;;32-bit tag value";
      }
    }
    leaf subnets {
      tailf:info
        "Consider subnets for redistribution into OSPF";
      type empty;
    }
  }

  grouping ncs_rpc_notif_ospf-redistribute-grouping {
    container redist-options {
      tailf:cli-drop-node-name;
      tailf:cli-compact-syntax;
      uses ncs_rpc_notif_ospf-iso-igrp-redistribute-grouping;
      leaf route-map {
        tailf:info
          "Route map reference";
        type string {
          tailf:info
            "WORD;;Pointer to route-map entries";
        }
      }
    }
  }

  grouping ncs_rpc_notif_ospf-redistribute-bgp-grouping {
    leaf as-number {
      tailf:cli-drop-node-name;
      type uint32 {
        range "1 .. 65535";
        tailf:info
          "<1-65535>;;Autonomous system number";
      }
    }
    uses ncs_rpc_notif_ospf-redistribute-grouping;
  }

  grouping ncs_rpc_notif_router-rip-grouping {
    uses ncs_rpc_notif_address-family-vrf-grouping;
    leaf flash-update-threshold {
      tailf:info
        "Specify flash update threshold in second";
      tailf:cli-full-command;
      type uint8 {
        range "0 .. 30";
        tailf:info
          "<0-30>;;threshold in seconds";
      }
    }
    leaf input-queue {
      tailf:info
        "Specify input queue depth";
      tailf:cli-full-command;
      type uint16 {
        range "0 .. 1024";
        tailf:info
          "0-1024;;queue depth";
      }
    }
    leaf output-delay {
      tailf:info
        "Interpacket delay for RIP updates";
      tailf:cli-full-command;
      type uint8 {
        range "8 .. 50";
        tailf:info
          "8-50;;Delay in milliseconds";
      }
    }
    uses ncs_rpc_notif_passive-interface-grouping;
    container traffic-share {
      tailf:info
        "How to compute traffic share over alternate paths";
      container min {
        tailf:info
          "All traffic shared among min metric paths";
        leaf across-interfaces {
          tailf:info
            "Use different interfaces for equal-cost paths";
          type empty;
        }
      }
    }
  }

  grouping ncs_rpc_notif_default-redistribute-grouping {
    container connected {
      presence "Connected";
      tailf:info
        "Connected";
      uses ncs_rpc_notif_rip-metric-route-map-grouping;
    }
    list bgp {
      tailf:info
        "Border Gateway Protocol (BGP)";
      tailf:cli-suppress-mode;
      tailf:cli-delete-when-empty;
      key "as-number";
      leaf as-number {
        type uint16 {
          range "1 .. 65535";
          tailf:info
            "<1-65535>;;Autonomous system number";
        }
      }
      uses ncs_rpc_notif_rip-metric-route-map-grouping;
    }
    list eigrp {
      tailf:info
        "Enhanced Interior Gateway Routing Protocol (EIGRP)";
      tailf:cli-suppress-mode;
      tailf:cli-delete-when-empty;
      key "as-number";
      leaf as-number {
        type uint16 {
          range "1 .. 65535";
          tailf:info
            "<1-65535>;;Autonomous system number";
        }
      }
      uses ncs_rpc_notif_rip-metric-route-map-grouping;
    }
    container isis {
      presence "ISO IS-IS";
      tailf:info
        "ISO IS-IS";
      list isis-area {
        tailf:cli-suppress-mode;
        tailf:cli-delete-when-empty;
        tailf:cli-drop-node-name;
        key "name";
        leaf name {
          tailf:cli-disallow-value "level-1|level-2|level-1-2|metric|route-map";
          type string {
            tailf:info
              "WORD;;ISO routing area tag";
          }
        }
        uses ncs_rpc_notif_redist-isis-grouping;
      }
      uses ncs_rpc_notif_redist-isis-grouping;
    }
    container iso-igrp {
      presence "IGRP for OSI networks";
      tailf:info
        "IGRP for OSI networks";
      list isoigrp-list {
        tailf:info
          "Border Gateway Protocol (BGP)";
        tailf:cli-suppress-mode;
        tailf:cli-delete-when-empty;
        tailf:cli-drop-node-name;
        key "iso-area-tag";
        leaf iso-area-tag {
          tailf:cli-disallow-value "route-map";
          type string {
            tailf:info
              "WORD;;ISO routing area tag";
          }
        }
        uses ncs_rpc_notif_rip-iso-igrp-metric-route-map-grouping;
      }
      uses ncs_rpc_notif_rip-iso-igrp-metric-route-map-grouping;
    }
    container mobile {
      presence "Mobile routes";
      tailf:info
        "Mobile routes";
      uses ncs_rpc_notif_rip-metric-route-map-grouping;
    }
    container odr {
      presence "On Demand stub Routes";
      tailf:info
        "On Demand stub Routes";
      uses ncs_rpc_notif_rip-metric-route-map-grouping;
    }
    list ospf {
      tailf:info
        "Open Shortest Path First (OSPF)";
      tailf:cli-suppress-mode;
      tailf:cli-delete-when-empty;
      key "process-id";
      leaf process-id {
        tailf:cli-suppress-range;
        type uint16 {
          range "1 .. 65535";
          tailf:info
            "<1-65535>;;Process ID";
        }
      }
      list vrf {
        tailf:info
          "VPN Routing/Forwarding Instance";
        tailf:cli-diff-dependency "/ios:ip/vrf" {
          tailf:xpath-root 3;
        }
        tailf:cli-diff-dependency "/ios:vrf/definition" {
          tailf:xpath-root 3;
        }
        key "name";
        leaf name {
          type string {
            tailf:info
              "WORD;;VPN Routing/Forwarding Instance (VRF) name";
          }
        }
      }
      container match {
        tailf:cli-compact-syntax;
        tailf:cli-flatten-container;
        tailf:info
          "Redistribution of OSPF routes";
        container internal {
          presence "Redistribute OSPF internal routes";
          tailf:info
            "Redistribute OSPF internal routes";
          tailf:cli-compact-syntax;
          tailf:cli-flatten-container;
          uses ncs_rpc_notif_rip-metric-route-map-grouping;
        }
        container external {
          tailf:info
            "Redistribute OSPF external routes";
          presence "Redistribute OSPF external routes";
          tailf:cli-compact-syntax;
          tailf:cli-flatten-container;
          leaf external-routes {
            tailf:cli-drop-node-name;
            type ncs_rpc_notif_redist-ospf-external-type;
          }
          uses ncs_rpc_notif_rip-metric-route-map-grouping;
        }
        container nssa-external {
          tailf:info
            "Redistribute OSPF NSSA external routes";
          presence "Redistribute OSPF NSSA external routes";
          tailf:cli-compact-syntax;
          tailf:cli-flatten-container;
          leaf nssa-external-routes {
            tailf:cli-drop-node-name;
            type ncs_rpc_notif_redist-ospf-external-type;
          }
          uses ncs_rpc_notif_rip-metric-route-map-grouping;
        }
      }
      uses ncs_rpc_notif_rip-metric-route-map-grouping;
    }
    container static {
      presence "Static routes";
      tailf:info
        "Static routes";
      uses ncs_rpc_notif_rip-metric-route-map-grouping;
    }
    container rip {
      presence "Routing Information Protocol (RIP)";
      tailf:info
        "Routing Information Protocol (RIP)";
      uses ncs_rpc_notif_rip-metric-route-map-grouping;
    }
  }

  grouping ncs_rpc_notif_distance-grouping {
    container distance {
      tailf:cli-compact-syntax;
      tailf:info
        "Define an administrative distance";
      leaf distance-leaf {
        tailf:cli-drop-node-name;
        tailf:cli-full-command;
        type uint8 {
          range "1..255";
          tailf:info
            "1-255;;Administrative distance";
        }
      }
      list distance-list {
        tailf:cli-suppress-mode;
        tailf:cli-delete-when-empty;
        tailf:cli-drop-node-name;
        key "number ip mask";
        leaf number {
          tailf:cli-suppress-range;
          type uint8 {
            range "1 .. 255";
            tailf:info
              "1-255;;Administrative distance";
          }
        }
        leaf ip {
          type inet:ipv4-address {
            tailf:info
              "A.B.C.D;;IP source address";
          }
        }
        leaf mask {
          type inet:ipv4-address {
            tailf:info
              "A.B.C.D;;Wildcard bits";
          }
        }
      }
    }
  }

  grouping ncs_rpc_notif_offset-list-grouping {
    list offset-list {
      tailf:info
        "Add or subtract offset from RIP metrics";
      tailf:cli-compact-syntax;
      tailf:cli-suppress-mode;
      tailf:cli-delete-when-empty;
      tailf:cli-suppress-list-no;
      tailf:cli-sequence-commands;
      key "in-out";
      leaf in-out {
        tailf:cli-incomplete-command;
        type ncs_rpc_notif_offset-list-in-out-type;
      }
      leaf offset {
        tailf:cli-drop-node-name;
        mandatory true;
        type uint8 {
          range "0 .. 16";
          tailf:info
            "<0-16>;;Offset";
        }
      }
    }
  }

  grouping ncs_rpc_notif_default-router-rip-grouping {
    leaf auto-summary {
      tailf:info
        "Enable automatic network number summarization";
      type empty;
    }
    leaf maximum-paths {
      tailf:cli-full-command;
      tailf:info
        "Forward packets over multiple paths";
      type uint8 {
        range "1 .. 32";
        tailf:info
          "1-32;;Number of paths";
      }
    }
    list neighbor {
      tailf:info
        "Specify a neighbor router";
      tailf:cli-suppress-mode;
      tailf:cli-delete-when-empty;
      key "ip";
      leaf ip {
        type inet:ipv4-address;
        tailf:info
          "A.B.C.D;;Neighbor address";
      }
    }
    list network {
      tailf:info
        "Enable routing on an IP network";
      tailf:cli-suppress-mode;
      tailf:cli-delete-when-empty;
      key "ip";
      leaf ip {
        type inet:ipv4-address;
        tailf:info
          "A.B.C.D;;Network number";
      }
    }
    leaf validate-update-source {
      tailf:info
        "Perform sanity checks against source address of routing updates";
      tailf:cli-full-command;
      tailf:cli-boolean-no;
      tailf:cli-trim-default;
      type boolean;
      default "true";
    }
  }

  grouping ncs_rpc_notif_address-family-vrf-grouping {
    uses ncs_rpc_notif_default-router-rip-grouping;
    container default-information {
      tailf:cli-incomplete-no;
      tailf:info
        "Control distribution of default information";
      container originate {
        tailf:cli-full-no;
        presence "Distribute a default route";
        tailf:info
          "Distribute a default route";
        leaf route-map {
          tailf:info
            "Route-map reference";
          tailf:cli-no-value-on-delete;
          type string {
            tailf:info
              "WORD;;Route map name";
          }
        }
      }
    }
    leaf default-metric {
      tailf:info
        "Set metric of redistributed routes";
      tailf:cli-full-command;
      type uint32 {
        range "1..4294967295";
        tailf:info
          "<1-4294967295>;;Default metric";
      }
    }
    uses ncs_rpc_notif_distance-grouping;
    uses ncs_rpc_notif_distribute-list-grouping;
    uses ncs_rpc_notif_offset-list-grouping;
    container redistribute {
      tailf:info
        "Redistribute information from another routing protocol";
      uses ncs_rpc_notif_rip-metric-route-map-grouping;
      uses ncs_rpc_notif_default-redistribute-grouping;
    }
    container timers {
      tailf:info
        "Adjust routing timers";
      tailf:cli-incomplete-no;
      tailf:cli-compact-syntax;
      container basic {
        tailf:info
          "Basic routing protocol update timers";
        tailf:cli-sequence-commands;
        tailf:cli-full-no;
        leaf updates {
          tailf:cli-drop-node-name;
          tailf:cli-incomplete-command;
          tailf:cli-no-value-on-delete;
          type uint32 {
            range "1 .. 4294967295";
            tailf:info
              "1-4294967295;;Interval between updates for RIP";
          }
        }
        leaf invalid {
          tailf:cli-drop-node-name;
          tailf:cli-incomplete-command;
          tailf:cli-no-value-on-delete;
          type uint32 {
            range "1 .. 4294967295";
            tailf:info
              "1-4294967295;;Invalid";
          }
        }
        leaf holddown {
          tailf:cli-drop-node-name;
          tailf:cli-incomplete-command;
          tailf:cli-no-value-on-delete;
          type uint32 {
            range "1 .. 4294967295";
            tailf:info
              "1-4294967295;;Holddown";
          }
        }
        leaf flush {
          tailf:cli-drop-node-name;
          tailf:cli-incomplete-command;
          tailf:cli-no-value-on-delete;
          type uint32 {
            range "1 .. 4294967295";
            tailf:info
              "1-4294967295;;Flush";
          }
        }
        leaf sleep {
          tailf:cli-drop-node-name;
          tailf:cli-no-value-on-delete;
          type uint32 {
            range "1 .. 4294967295";
            tailf:info
              "1-4294967295;;Sleep time, in milliseconds";
          }
        }
      }
    }
    leaf version {
      tailf:info
        "Set routing protocol version";
      type uint8 {
        range "1 .. 2";
        tailf:info
          "1-2;;rip version 1 or 2";
      }
    }
  }

  grouping ncs_rpc_notif_redist-isis-grouping {
    container rip-isis-redist {
      tailf:cli-drop-node-name;
      leaf isis-level-routes {
        tailf:cli-drop-node-name;
        type enumeration {
          enum "level-1" {
            tailf:info
              "IS-IS level-1 routes only";
          }
          enum "level-2" {
            tailf:info
              "IS-IS level-2 routes only";
          }
          enum "level-1-2" {
            tailf:info
              "IS-IS level-1 and level-2 routes";
          }
        }
      }
      uses ncs_rpc_notif_rip-metric-route-map-grouping;
    }
  }

  grouping ncs_rpc_notif_rip-metric-route-map-grouping {
    container rip-metric-route-map {
      tailf:cli-drop-node-name;
      tailf:cli-compact-syntax;
      container metric {
        tailf:cli-compact-syntax;
        tailf:cli-flatten-container;
        tailf:info
          "Metric for redistributed routes";
        choice metric-transparent-choice {
          leaf metric-value {
            tailf:cli-drop-node-name;
            tailf:info
              "Metric for redistributed routes";
            type uint32 {
              range "0 .. 16";
              tailf:info
                "<0-16>;;Default metric";
            }
          }
          leaf transparent {
            tailf:info
              "Transparently redistribute metric";
            type empty;
          }
        }
      }
      leaf route-map {
        tailf:info
          "Route map reference";
        type string {
          tailf:info
            "WORD;;Pointer to route-map entries";
        }
      }
    }
  }

  grouping ncs_rpc_notif_rip-iso-igrp-metric-route-map-grouping {
    container rip-metric-route-map {
      tailf:cli-drop-node-name;
      tailf:cli-compact-syntax;
      tailf:cli-sequence-commands;
      leaf route-map {
        tailf:info
          "Route map reference";
        type string {
          tailf:info
            "WORD;;Pointer to route-map entries";
        }
      }
      container metric {
        tailf:cli-compact-syntax;
        tailf:info
          "Metric for redistributed routes";
        choice metric-transparent-choice {
          leaf metric-value {
            tailf:cli-drop-node-name;
            tailf:info
              "Metric for redistributed routes";
            type uint32 {
              range "0 .. 16";
              tailf:info
                "<0-16>;;Default metric";
            }
          }
          leaf transparent {
            tailf:info
              "Transparently redistribute metric";
            type empty;
          }
        }
      }
    }
  }

  grouping ncs_rpc_notif_narrow-wide-transition-grouping {
    leaf narrow-wide {
      tailf:cli-drop-node-name;
      tailf:cli-full-command;
      type ncs_rpc_notif_isis-level-type;
    }
    leaf transition {
      tailf:info
        "Accept both styles of TLVs during transition";
      type ncs_rpc_notif_isis-level-type;
      tailf:cli-full-command;
    }
  }

  grouping ncs_rpc_notif_spf-intervals-grouping {
    leaf interval {
      tailf:cli-drop-node-name;
      type uint32 {
        range "1 .. 120";
        tailf:info
          "<1-120>;;Interval between consecutive SPFs in seconds";
      }
    }
    leaf initial-wait {
      tailf:cli-drop-node-name;
      type uint32 {
        range "1 .. 120000";
        tailf:info
          "<1-120000>;;Initial wait before first SPF in milliseconds";
      }
    }
    leaf minimum-wait {
      tailf:cli-drop-node-name;
      type uint32 {
        range "1 .. 120000";
        tailf:info
          "<1-120000>;;Minimum wait between first and second SPF in milliseconds";
      }
    }
  }

  grouping ncs_rpc_notif_authenticate-snp-grouping {
    leaf authenticate {
      tailf:info
        "Authentication";
      tailf:cli-incomplete-command;
      type empty;
    }
    leaf snp {
      tailf:info
        "SNP PDUs";
      type enumeration {
        enum "send-only" {
          tailf:info
            "Send but do not check PDUs on receiving";
        }
        enum "validate" {
          tailf:info
            "Send and check PDUs on receiving";
        }
      }
    }
  }

  grouping ncs_rpc_notif_lsp-gen-interval-grouping {
    leaf interval {
      tailf:cli-drop-node-name;
      type uint32 {
        range "1 .. 120";
        tailf:info
          "<1-120>;;Interval in seconds";
      }
    }
    leaf initial-wait {
      tailf:cli-drop-node-name;
      type uint32 {
        range "1 .. 120000";
        tailf:info
          "<1-120000>;;Initial wait in milliseconds";
      }
    }
    leaf wait {
      tailf:cli-drop-node-name;
      type uint32 {
        range "1 .. 120000";
        tailf:info
          "<1-120000>;;Wait between first and second lsp generation in milliseconds";
      }
    }
  }

  grouping ncs_rpc_notif_set-overload-bit-suppress-grouping {
    leaf external {
      tailf:info
        "If overload-bit set, don't advertise IP prefixes learned from other protocols";
      tailf:cli-break-sequence-commands;
      type empty;
    }
    leaf interlevel {
      tailf:info
        "If overload-bit set, don't advertise IP prefixes learned from another ISIS level";
      type empty;
    }
  }

  grouping ncs_rpc_notif_summary-address-metric-tag-grouping {
    leaf metric {
      tailf:info
        "Set metric for summay route";
      tailf:cli-full-command;
      type uint32 {
        range "1 .. 4294967295";
        tailf:info
          "<1-4294967295>;;metric";
      }
    }
    leaf tag {
      tailf:info
        "Set tag";
      type uint32 {
        range "1 .. 4294967295";
        tailf:info
          "<1-4294967295>;;32-bit tag value";
      }
    }
  }

  grouping ncs_rpc_notif_authentication-level-grouping {
    leaf levels {
      tailf:cli-drop-node-name;
      type ncs_rpc_notif_authentication-level-type;
    }
  }

  grouping ncs_rpc_notif_redist-level-grouping {
    leaf levels {
      tailf:cli-drop-node-name;
      tailf:cli-break-sequence-commands;
      type ncs_rpc_notif_isis-routes-level-type;
    }
  }

  grouping ncs_rpc_notif_isis-redist-container-content-grouping {
    uses ncs_rpc_notif_redist-level-grouping;
    leaf metric {
      tailf:info
        "ISIS default metric";
      type uint32 {
        range "0 .. 4294967295";
        tailf:info
          "<0-4294967295>;;ISIS default metric";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
    }
    leaf route-map {
      tailf:info
        "Route map reference";
      type string {
        tailf:info
          "WORD;;Pointer to route-map entries";
      }
    }
  }

  grouping ncs_rpc_notif_isis-redist-grouping {
    container isis-redist-container {
      tailf:cli-drop-node-name;
      uses ncs_rpc_notif_isis-redist-container-content-grouping;
    }
  }

  grouping ncs_rpc_notif_isis-redist-af-grouping {
    container isis-redist-af-container {
      tailf:cli-drop-node-name;
      leaf include-connected {
        tailf:info
          "Include connected";
        type empty;
      }
      uses ncs_rpc_notif_isis-redist-container-content-grouping;
    }
  }

  grouping ncs_rpc_notif_isis-redist-ospf-match-grouping {
    uses ncs_rpc_notif_redist-level-grouping;
    leaf metric {
      tailf:info
        "ISIS default metric";
      type uint32 {
        range "0 .. 4294967295";
        tailf:info
          "<0-4294967295>;;ISIS default metric";
      }
    }
    leaf route-map {
      tailf:info
        "Route map reference";
      type string {
        tailf:info
          "WORD;;Pointer to route-map entries";
      }
    }
  }

  grouping ncs_rpc_notif_isis-redist-clns-ip-grouping {
    uses ncs_rpc_notif_isis-redist-grouping;
    container clns {
      tailf:info
        "Redistribution of BGP NSAP routes";
      presence "Redistribution of BGP NSAP routes";
      leaf route-map {
        tailf:info
          "Route map reference";
        type string {
          tailf:info
            "WORD;;Pointer to route-map entries";
        }
      }
    }
    leaf ip {
      tailf:info
        "Redistribution of BGP IP routes";
      type empty;
    }
  }

  grouping ncs_rpc_notif_isis-address-family-grouping {
    leaf adjacency-check {
      tailf:info
        "Check ISIS neighbor protocol support";
      type empty;
      tailf:cli-full-command;
    }
    container default-information {
      tailf:cli-incomplete-no;
      tailf:info
        "Control distribution of default information";
      container originate {
        tailf:cli-full-no;
        presence "Distribute a default route";
        tailf:info
          "Distribute a default route";
        leaf route-map {
          tailf:info
            "Route-map reference";
          tailf:cli-no-value-on-delete;
          type string {
            tailf:info
              "WORD;;Route map name";
          }
        }
      }
    }
    leaf maximum-paths {
      tailf:info
        "Forward packets over multiple paths";
      tailf:cli-full-command;
      type uint32 {
        range "1 .. 32";
        tailf:info
          "<1-32>;;Number of paths";
      }
    }
    container metric {
      tailf:info
        "Set ISIS metric for all interfaces";
      tailf:cli-compact-syntax;
      tailf:cli-sequence-commands;
      leaf default {
        tailf:cli-drop-node-name;
        type uint32 {
          range "1 .. 63";
          tailf:info
            "<1-63>;;Default metric";
        }
      }
      leaf level-1-2 {
        tailf:cli-drop-node-name;
        type enumeration {
          enum "level-1" {
            tailf:info
              "Apply metric to level-1 links";
          }
          enum "level-2" {
            tailf:info
              "Apply metric to level-2 links";
          }
        }
      }
    }
    container prc-interval {
      tailf:info
        "Minimum interval between partial route calculations";
      tailf:cli-compact-syntax;
      tailf:cli-sequence-commands;
      leaf interval {
        tailf:cli-drop-node-name;
        type uint32 {
          range "1 .. 120";
          tailf:info
            "<1-120>;;PRC interval in seconds";
        }
      }
      leaf initial-wait {
        tailf:cli-drop-node-name;
        type uint32 {
          range "1 .. 120000";
          tailf:info
            "<1-120000>;;Initial wait for PRC in milliseconds";
        }
      }
      leaf minimum-wait {
        tailf:cli-drop-node-name;
        type uint32 {
          range "1 .. 120000";
          tailf:info
            "<1-120000>;;Minimum wait between first and second PRC in milliseconds";
        }
      }
    }
    container set-overload-bit {
      tailf:info
        "Signal other routers not to use us in SPF";
      choice set-overload-bit-choice {
        container on-startup {
          tailf:info
            "Set overload-bit only temporarily after reboot";
          choice on-startup-choice {
            container time {
              tailf:cli-drop-node-name;
              tailf:cli-compact-syntax;
              tailf:cli-sequence-commands;
              leaf time {
                tailf:cli-drop-node-name;
                type uint32 {
                  range "5 .. 86400";
                  tailf:info
                    "<5-86400>;;Time in seconds to advertise ourself as overloaded after reboot";
                }
              }
              leaf suppress {
                tailf:info
                  "If overload-bit set, suppress the following types of IP prefixes";
                tailf:cli-incomplete-command;
                type empty;
              }
              uses ncs_rpc_notif_set-overload-bit-suppress-grouping;
            }
            container wait-for-bgp {
              tailf:info
                "Let BGP decide when to unset the overload bit";
              presence "Let BGP decide when to unset the overload bitW";
              container suppress {
                tailf:info
                  "If overload-bit set, suppress the following types of IP prefixes";
                tailf:cli-compact-syntax;
                uses ncs_rpc_notif_set-overload-bit-suppress-grouping;
              }
            }
          }
        }
        container suppress {
          tailf:info
            "If overload-bit set, suppress the following types of IP prefixes";
          tailf:cli-compact-syntax;
          uses ncs_rpc_notif_set-overload-bit-suppress-grouping;
        }
      }
    }
    container spf-interval {
      tailf:info
        "Minimum interval between SPF calculations";
      tailf:cli-compact-syntax;
      choice spf-interval-choice {
        list level-1-2 {
          tailf:cli-drop-node-name;
          tailf:cli-suppress-mode;
          tailf:cli-delete-when-empty;
          tailf:cli-compact-syntax;
          tailf:cli-sequence-commands;
          tailf:cli-incomplete-command;
          key "level";
          leaf level {
            type enumeration {
              enum "level-1" {
                tailf:info
                  "Set interval for level 1 only";
              }
              enum "level-2" {
                tailf:info
                  "Set interval for level 2 only";
              }
            }
          }
          uses ncs_rpc_notif_spf-intervals-grouping;
        }
        container intervals {
          tailf:cli-drop-node-name;
          tailf:cli-compact-syntax;
          tailf:cli-sequence-commands;
          uses ncs_rpc_notif_spf-intervals-grouping;
        }
      }
    }
    container traffic-share {
      tailf:info
        "How to compute traffic share over alternate paths";
      container min {
        tailf:info
          "All traffic shared among min metric paths";
        leaf across-interface {
          tailf:info
            "Use different interfaces for equal-cost paths";
          type empty;
        }
      }
    }
  }

  grouping ncs_rpc_notif_isis-main-grouping {
    container isis-main-container {
      tailf:cli-full-command;
      tailf:cli-drop-node-name;
      uses ncs_rpc_notif_isis-address-family-grouping;
      container address-family {
        tailf:info
          "Enter Address Family command mode";
        container ipv6 {
          tailf:info
            "Address family";
          container unicast {
            tailf:cli-add-mode;
            tailf:cli-mode-name "config-router-af";
            tailf:info
              "Address Family Modifier";
            tailf:cli-full-command;
            tailf:cli-exit-command "exit-address-family" {
              tailf:info
                "Exit from Address Family configuration mode";
            }
            uses ncs_rpc_notif_isis-address-family-grouping;
            leaf distance {
              tailf:info
                "Administrative distance";
              tailf:cli-full-command;
              type uint32 {
                range "1 .. 255";
                tailf:info
                  "<1-255>;;OSPF Administrative distance";
              }
            }
            container multi-topology {
              tailf:info
                "Enable multi-topology mode";
              presence "Enable multi-topology mode";
              leaf transition {
                tailf:info
                  "Accept and generate both IS-IS IPv6 and Multi-topology IPv6 TLVs";
                type empty;
              }
            }
            container redistribute {
              tailf:info
                "Redistribute IPv6 prefixes from another routing protocol";
              container bgp {
                tailf:info
                  "Border Gateway Protocol (BGP)";
                tailf:cli-sequence-commands;
                tailf:cli-compact-syntax;
                leaf as-number {
                  tailf:cli-drop-node-name;
                  type uint32 {
                    range "1 .. 65535";
                    tailf:info
                      "<1-65535>;;Autonomous system number";
                  }
                }
                uses ncs_rpc_notif_isis-redist-af-grouping;
              }
              container connected {
                tailf:info
                  "Connected";
                presence "Connected";
                uses ncs_rpc_notif_isis-redist-grouping;
              }
              list eigrp {
                tailf:info
                  "Enhanced Interior Gateway Routing Protocol (EIGRP)";
                tailf:cli-suppress-mode;
                tailf:cli-delete-when-empty;
                key "as-number";
                leaf as-number {
                  tailf:cli-drop-node-name;
                  type uint32 {
                    range "1 .. 65535";
                    tailf:info
                      "<1-65535>;;Autonomous system number";
                  }
                }
                uses ncs_rpc_notif_isis-redist-af-grouping;
              }
              container isis {
                tailf:info
                  "ISO IS-IS";
                tailf:cli-compact-syntax;
                leaf area-tag {
                  tailf:cli-drop-node-name;
                  tailf:cli-disallow-value "level-1|level-2";
                  type string {
                    tailf:info
                      "WORD;;IPv6 process name";
                  }
                }
                container levels {
                  tailf:cli-drop-node-name;
                  tailf:cli-sequence-commands;
                  leaf isis-redist-levels1 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf into {
                    tailf:info
                      "from level-n into level-m";
                    tailf:cli-incomplete-command;
                    type empty;
                  }
                  leaf isis-redist-levels2 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf distribute-list {
                    tailf:info
                      "select routes";
                    type string {
                      tailf:info
                        "WORD;;IPv6 prefix-list name";
                    }
                  }
                }
              }
              container nemo {
                tailf:info
                  "Network Mobility (NEMO)";
                tailf:cli-compact-syntax;
                uses ncs_rpc_notif_isis-redist-af-grouping;
              }
              list ospf {
                tailf:info
                  "Open Shortest Path First (OSPF)";
                tailf:cli-suppress-mode;
                tailf:cli-delete-when-empty;
                key "process-id";
                leaf process-id {
                  tailf:cli-suppress-range;
                  type uint32 {
                    range "1 .. 65535";
                    tailf:info
                      "<1-65535>;;Process ID";
                  }
                }
                uses ncs_rpc_notif_isis-redist-af-grouping;
                container match {
                  tailf:cli-compact-syntax;
                  tailf:cli-flatten-container;
                  tailf:info
                    "Redistribution of OSPF routes";
                  container internal {
                    presence "Redistribute OSPF internal routes";
                    tailf:info
                      "Redistribute OSPF internal routes";
                    tailf:cli-compact-syntax;
                    tailf:cli-flatten-container;
                    uses ncs_rpc_notif_isis-redist-ospf-match-grouping;
                  }
                  container external {
                    tailf:info
                      "Redistribute OSPF external routes";
                    presence "Redistribute OSPF external routes";
                    tailf:cli-compact-syntax;
                    tailf:cli-flatten-container;
                    leaf external-routes {
                      tailf:cli-drop-node-name;
                      type ncs_rpc_notif_redist-ospf-external-type;
                    }
                    uses ncs_rpc_notif_isis-redist-ospf-match-grouping;
                  }
                  container nssa-external {
                    tailf:info
                      "Redistribute OSPF NSSA external routes";
                    presence "Redistribute OSPF NSSA external routes";
                    tailf:cli-compact-syntax;
                    tailf:cli-flatten-container;
                    leaf nssa-external-routes {
                      tailf:cli-drop-node-name;
                      type ncs_rpc_notif_redist-ospf-external-type;
                    }
                    uses ncs_rpc_notif_isis-redist-ospf-match-grouping;
                  }
                }
              }
              list rip {
                tailf:info
                  "IPv6 Routing Information Protocol (RIPv6)";
                tailf:cli-suppress-mode;
                tailf:cli-delete-when-empty;
                key "process";
                leaf process {
                  type string {
                    tailf:info
                      "WORD;;User selected string identifying this process";
                  }
                }
                uses ncs_rpc_notif_isis-redist-af-grouping;
              }
              container static {
                tailf:info
                  "Static routes";
                presence "Static routes";
                uses ncs_rpc_notif_isis-redist-grouping;
              }
            }
            list summary-prefix {
              tailf:info
                "Configure IPv6 summary prefix";
              tailf:cli-suppress-mode;
              tailf:cli-delete-when-empty;
              key "prefix";
              leaf prefix {
                type inet:ipv6-prefix {
                  tailf:info
                    "X:X:X:X::X/<0-128>;;IPv6 prefix x:x::y/<z>";
                }
              }
              leaf levels {
                tailf:cli-drop-node-name;
                type enumeration {
                  enum "level-1" {
                    tailf:info
                      "Summarize into level-1 area";
                  }
                  enum "level-1-2" {
                    tailf:info
                      "Summarize into both area and sub-domain";
                  }
                  enum "level-2" {
                    tailf:info
                      "Summarize into level-2 sub-domain";
                  }
                }
              }
            }
          }
        }
      }
      container advertise {
        tailf:info
          "Control which IP routes flow in L1 and L2 LSPs";
        leaf passive-only {
          tailf:info
            "only interface address of passive interfaces";
          type empty;
        }
      }
      container area-password {
        tailf:info
          "Configure the authentication password for an area";
        tailf:cli-sequence-commands;
        tailf:cli-compact-syntax;
        leaf name {
          tailf:cli-drop-node-name;
          type string {
            tailf:info
              "WORD;;Area password";
          }
        }
        uses ncs_rpc_notif_authenticate-snp-grouping;
      }
      container authentication {
        tailf:info
          "ISIS authentication for LSPs";
        container mode {
          tailf:info
            "Authentication mode";
          container md5 {
            tailf:info
              "Keyed message digest";
            presence "Keyed message digest";
            uses ncs_rpc_notif_authentication-level-grouping;
          }
          container text {
            tailf:info
              "Clear text password";
            presence "Clear text password";
            uses ncs_rpc_notif_authentication-level-grouping;
          }
        }
        container key-chain {
          tailf:info
            "Authentication key-chain";
          tailf:cli-compact-syntax;
          tailf:cli-sequence-commands;
          leaf name {
            tailf:cli-drop-node-name;
            type string {
              tailf:info
                "WORD;;Name of key-chain";
            }
          }
          uses ncs_rpc_notif_authentication-level-grouping;
        }
        container send-only {
          tailf:info
            "Authentication send only, receive ignore";
          presence "Authentication send only, receive ignore";
          uses ncs_rpc_notif_authentication-level-grouping;
        }
      }
      container bfd {
        tailf:info
          "BFD configuration commands";
        leaf all-interfaces {
          tailf:info
            "Enable BFD on all interfaces";
          type empty;
        }
      }
      container distance {
        tailf:info
          "Define an administrative distance";
        tailf:cli-compact-syntax;
        container clns-container {
          tailf:cli-drop-node-name;
          tailf:cli-sequence-commands;
          leaf distance {
            tailf:cli-drop-node-name;
            type uint32 {
              range "1 .. 255";
              tailf:info
                "<1-255>;;OSPF Administrative distance";
            }
          }
          leaf clns {
            tailf:info
              "Distance applied for CLNS derived routes";
            tailf:cli-full-command;
            type empty;
          }
        }
        container ip-container {
          tailf:cli-drop-node-name;
          tailf:cli-sequence-commands;
          leaf distance {
            tailf:cli-drop-node-name;
            type uint32 {
              range "1 .. 255";
              tailf:info
                "<1-255>;;OSPF Administrative distance";
            }
          }
          leaf ip {
            tailf:info
              "Distance applied for IP derived routes";
            tailf:cli-full-command;
            type empty;
          }
        }
        container acl-container {
          tailf:cli-drop-node-name;
          tailf:cli-sequence-commands;
          leaf distance {
            tailf:cli-drop-node-name;
            type uint32 {
              range "1 .. 255";
              tailf:info
                "<1-255>;;OSPF Administrative distance";
            }
          }
          list acl {
            tailf:cli-drop-node-name;
            tailf:cli-suppress-mode;
            tailf:cli-delete-when-empty;
            key "ip wildcard";
            leaf ip {
              type inet:ipv4-address {
                tailf:info
                  "A.B.C.D;;IP source address";
              }
            }
            leaf wildcard {
              type inet:ipv4-address {
                tailf:info
                  "A.B.C.D;;Wildcard bits";
              }
            }
            leaf acl-name {
              tailf:cli-drop-node-name;
              type ncs_rpc_notif_access-list-standard-id-type;
              tailf:cli-no-value-on-delete;
            }
          }
        }
      }
      container domain-password {
        tailf:info
          "Set the authentication password for a routing domain";
        tailf:cli-sequence-commands;
        tailf:cli-compact-syntax;
        leaf name {
          tailf:cli-drop-node-name;
          type string {
            tailf:info
              "WORD;;Routing domain password";
          }
        }
        uses ncs_rpc_notif_authenticate-snp-grouping;
      }
      container fast-flood {
        tailf:info
          "Flood LSPs (that triggered SPF) before running SPF";
        presence "Flood LSPs (that triggered SPF) before running SPF";
        leaf number {
          tailf:cli-drop-node-name;
          type uint32 {
            range "1 .. 15";
            tailf:info
              "<1-15>;;number of LSPs to be flooded before starting SPF";
          }
        }
      }
      container hello {
        tailf:info
          "Pad ISIS hello PDUs to full MTU";
        container padding {
          tailf:info
            "Pad hello PDU";
          presence "Pad hello PDU";
          leaf pad-type {
            tailf:cli-drop-node-name;
            type enumeration {
              enum "multi-point" {
                tailf:info
                  "Pad LAN hello PDUs";
              }
              enum "point-to-point" {
                tailf:info
                  "Pad point-to-point hello PDUs";
              }
            }
          }
        }
      }
      container hostname {
        tailf:info
          "Dynamic hostname for IS-IS";
        leaf dynamic {
          tailf:info
            "Dynamic hostname";
          type empty;
        }
      }
      leaf ignore-lsp-errors {
        tailf:info
          "Ignore LSPs with bad checksums";
        tailf:cli-full-command;
        type empty;
      }
      container ip {
        tailf:info
          "IP specific commands";
        container route {
          tailf:info
            "ISIS IP routes";
          container priority {
            tailf:info
              "Assign priority to IP prefixes";
            container high {
              tailf:info
                "Assign high priority to important IP prefixes in ISIS IP local RIB";
              leaf tag {
                tailf:info
                  "Assign high priority to IP prefixes with a specific route tag";
                type uint32 {
                  range "1 .. 4294967295";
                  tailf:info
                    "<1-4294967295>;;tag value";
                }
              }
            }
          }
        }
      }
      leaf is-type {
        tailf:info
          "IS Level for this routing process (OSI only)";
        tailf:cli-full-command;
        type enumeration {
          enum "level-1" {
            tailf:info
              "Act as a station router only";
          }
          enum "level-1-2" {
            tailf:info
              "Act as both a station router and an area router";
          }
          enum "level-2-only" {
            tailf:info
              "Act as an area router only";
          }
        }
      }
      container ispf {
        tailf:info
          "Configure execution of incremental SPF";
        tailf:cli-compact-syntax;
        tailf:cli-sequence-commands;
        leaf level {
          tailf:cli-drop-node-name;
          type enumeration {
            enum "level-1" {
              tailf:info
                "Do incremental SPF for level-1";
            }
            enum "level-1-2" {
              tailf:info
                "Do incremental SPF for both levels";
            }
            enum "level-2" {
              tailf:info
                "Do incremental SPF for level-2";
            }
          }
        }
        leaf number {
          tailf:cli-drop-node-name;
          type uint32 {
            range "1 .. 600";
            tailf:info
              "<1-600>;;Number of seconds before activating incremental-spf";
          }
        }
      }
      container log-adjacency-changes {
        tailf:info
          "Log changes in adjacency state";
        presence "Log changes in adjacency state";
        leaf all {
          tailf:info
            "Include changes generated by non-IIH event";
          type empty;
        }
      }
      container lsp-full {
        tailf:info
          "If we run out of LSP fragments";
        container suppress {
          tailf:info
            "suppress the following types of IP prefixes";
          choice lsp-full-choince {
            container external-interlevel-container {
              tailf:cli-drop-node-name;
              tailf:cli-compact-syntax;
              leaf external {
                tailf:info
                  "don't advertise IP prefixes learned from other protocols";
                type empty;
              }
              leaf interlevel {
                tailf:info
                  "don't advertise IP prefixes learned from another ISIS level";
                type empty;
              }
            }
            leaf none {
              tailf:info
                "don't suppress any prefixes";
              type empty;
            }
          }
        }
      }
      container lsp-gen-interval {
        tailf:info
          "Minimum interval between regenerating same LSP";
        choice lsp-gen-interval-choice {
          container intervals {
            tailf:cli-drop-node-name;
            tailf:cli-compact-syntax;
            tailf:cli-sequence-commands;
            uses ncs_rpc_notif_lsp-gen-interval-grouping;
          }
          container intervals-levels {
            tailf:cli-drop-node-name;
            container intervals-level-1 {
              tailf:cli-drop-node-name;
              tailf:cli-compact-syntax;
              tailf:cli-sequence-commands;
              leaf level-1 {
                tailf:info
                  "Set interval for level 1 only";
                type empty;
              }
              uses ncs_rpc_notif_lsp-gen-interval-grouping;
            }
            container intervals-level-2 {
              tailf:cli-drop-node-name;
              tailf:cli-compact-syntax;
              tailf:cli-sequence-commands;
              leaf level-2 {
                tailf:info
                  "Set interval for level 2 only";
                type empty;
              }
              uses ncs_rpc_notif_lsp-gen-interval-grouping;
            }
          }
        }
      }
      leaf lsp-mtu {
        tailf:info
          "Set maximum LSP size";
        tailf:cli-full-command;
        type uint32 {
          range "128 .. 4352";
          tailf:info
            "<128-4352>;;Max LSP size in bytes";
        }
      }
      leaf lsp-refresh-interval {
        tailf:info
          "Set LSP refresh interval";
        tailf:cli-full-command;
        type uint32 {
          range "1 .. 65535";
          tailf:info
            "<1-65535>;;LSP refresh time in seconds";
        }
      }
      leaf max-area-addresses {
        tailf:info
          "Allow configuration of more manual area addresses";
        tailf:cli-full-command;
        type uint32 {
          range "3 .. 254";
          tailf:info
            "<3-254>;;Max number of manual area addresses";
        }
      }
      leaf max-lsp-lifetime {
        tailf:info
          "Set maximum LSP lifetime";
        tailf:cli-full-command;
        type uint32 {
          range "1 .. 65535";
          tailf:info
            "<1-65535>;;Maximum LSP lifetime in seconds";
        }
      }
      container metric-style {
        tailf:info
          "Use old-style (ISO 10589) or new-style packet formats";
        choice metric-style-choice {
          container narrow {
            tailf:info
              "Use old style of TLVs with narrow metric";
            presence "true";
            uses ncs_rpc_notif_narrow-wide-transition-grouping;
          }
          container transition {
            tailf:info
              "Send and accept both styles of TLVs during transition";
            presence "true";
            leaf transition {
              type ncs_rpc_notif_isis-level-type;
              tailf:cli-drop-node-name;
            }
          }
          container wide {
            tailf:info
              "Use new style of TLVs to carry wider metric";
            presence "true";
            uses ncs_rpc_notif_narrow-wide-transition-grouping;
          }
        }
      }
      container mpls {
        tailf:info
          "Configure MPLS routing protocol parameters";
        container traffic-eng {
          tailf:info
            "routing protocol commands for MPLS Traffic Engineering";
          leaf level-1 {
            tailf:info
              "Run MPLS TE on IS-IS level 1 only";
            tailf:cli-full-command;
            type empty;
          }
          leaf level-2 {
            tailf:info
              "Run MPLS TE on IS-IS level 2 only";
            tailf:cli-full-command;
            type empty;
          }
          leaf multicast-intact {
            tailf:info
              "MPLS TE and PIM interaction";
            tailf:cli-full-command;
            type empty;
          }
          container router-id {
            tailf:info
              "Traffic Engineering stable IP address for system";
            tailf:cli-diff-dependency "/ios:interface" {
              tailf:xpath-root 3;
            }
            uses ncs_rpc_notif_interface-grouping;
          }
          container scanner {
            tailf:info
              "Timer parameters for TE database";
            presence "Timer parameters for TE database";
            tailf:cli-compact-syntax;
            leaf interval {
              tailf:info
                "time (secs) between LSPDB walks for TE";
              type uint32 {
                range "1 .. 60";
                tailf:info
                  "<1-60>;;interval between LSPDB walks for TE TLVs extraction";
              }
            }
            leaf max-flash {
              tailf:info
                "Number of ISIS LSPs to be processed with no delay";
              type uint32 {
                range "0 .. 200";
                tailf:info
                  "<0-200>;;Max. number of LSPs ISIS may send to TE db without delay";
              }
            }
          }
        }
      }
      list net {
        tailf:info
          "A Network Entity Title for this process (OSI only)";
        tailf:cli-suppress-mode;
        tailf:cli-delete-when-empty;
        key "tag";
        leaf tag {
          type ncs_rpc_notif_isis-net;
        }
      }
      container partition {
        tailf:info
          "CLNS area partition";
        leaf avoidance {
          tailf:info
            "Withdraw area prefix if partition detected";
          type empty;
        }
      }
      uses ncs_rpc_notif_passive-interface-grouping;
      container protocol {
        tailf:info
          "Set protocol's administrative state";
        leaf shutdown {
          tailf:info
            "Set protocol's administrative state to disable";
          type empty;
        }
      }
      container redistribute {
        tailf:info
          "Redistribute information from another routing protocol";
        uses ncs_rpc_notif_isis-redist-grouping;
        container bgp {
          tailf:info
            "Border Gateway Protocol (BGP)";
          tailf:cli-sequence-commands;
          tailf:cli-compact-syntax;
          leaf as-number {
            tailf:cli-drop-node-name;
            type uint32 {
              range "1 .. 65535";
              tailf:info
                "<1-65535>;;Autonomous system number";
            }
          }
          uses ncs_rpc_notif_isis-redist-clns-ip-grouping;
        }
        container connected {
          tailf:info
            "Connected";
          presence "Connected";
          uses ncs_rpc_notif_isis-redist-grouping;
        }
        list eigrp {
          tailf:info
            "Enhanced Interior Gateway Routing Protocol (EIGRP)";
          tailf:cli-suppress-mode;
          tailf:cli-delete-when-empty;
          key "as-number";
          leaf as-number {
            tailf:cli-drop-node-name;
            type uint32 {
              range "1 .. 65535";
              tailf:info
                "<1-65535>;;Autonomous system number";
            }
          }
          uses ncs_rpc_notif_isis-redist-grouping;
        }
        container isis {
          tailf:info
            "ISO IS-IS";
          tailf:cli-compact-syntax;
          leaf area-tag {
            tailf:cli-full-command;
            tailf:cli-drop-node-name;
            tailf:cli-disallow-value "ip";
            type string {
              tailf:info
                "WORD;;ISO routing area tag";
            }
          }
          container ip {
            tailf:info
              "Redistribution of IP routes between levels";
            tailf:cli-compact-syntax;
            tailf:cli-sequence-commands;
            leaf isis-redist-levels1 {
              tailf:cli-drop-node-name;
              tailf:cli-incomplete-command;
              type enumeration {
                enum "level-1" {
                  tailf:info
                    "Inter-area routes from level-1";
                }
                enum "level-2" {
                  tailf:info
                    "Inter-area routes from level-2";
                }
              }
            }
            leaf into {
              tailf:info
                "from level-n into level-m";
              tailf:cli-incomplete-command;
              type empty;
            }
            leaf isis-redist-levels2 {
              tailf:cli-drop-node-name;
              tailf:cli-incomplete-command;
              type enumeration {
                enum "level-1" {
                  tailf:info
                    "Inter-area routes from level-1";
                }
                enum "level-2" {
                  tailf:info
                    "Inter-area routes from level-2";
                }
              }
            }
            choice isis-redist-isis-ip-choice {
              leaf distribute-list {
                tailf:info
                  "select routes";
                type uint32 {
                  range "100 .. 199";
                  tailf:info
                    "<100-199>;;IP extended acces-list number";
                }
              }
              leaf route-map {
                tailf:info
                  "Route map for route matching";
                type string {
                  tailf:info
                    "WORD;;Name of the route-map";
                }
              }
            }
          }
        }
        container iso-igrp {
          tailf:info
            "IGRP for OSI networks";
          presence "IGRP for OSI networks";
          tailf:cli-sequence-commands;
          choice iso-igrp-choice {
            container area-tag-route-map-container {
              tailf:cli-drop-node-name;
              tailf:cli-sequence-commands;
              tailf:cli-flatten-container;
              leaf area-tag {
                tailf:cli-drop-node-name;
                tailf:cli-disallow-value "route-map";
                type string {
                  tailf:info
                    "WORD;;ISO routing area tag";
                }
              }
              leaf route-map {
                tailf:info
                  "Route map reference";
                type string {
                  tailf:info
                    "WORD;;Pointer to route-map entries";
                }
              }
            }
            leaf route-map {
              tailf:info
                "Route map reference";
              type string {
                tailf:info
                  "WORD;;Pointer to route-map entries";
              }
            }
          }
          uses ncs_rpc_notif_redist-level-grouping;
          leaf metric {
            tailf:info
              "ISIS default metric";
            type uint32 {
              range "0 .. 4294967295";
              tailf:info
                "<0-4294967295>;;ISIS default metric";
            }
          }
          leaf metric-type {
            tailf:info
              "OSPF/IS-IS exterior metric type for redistributed routes";
            type enumeration {
              enum "external" {
                tailf:info
                  "Set IS-IS External metric type";
              }
              enum "internal" {
                tailf:info
                  "Set IS-IS Internal metric type";
              }
            }
          }
        }
        container maximum-prefix {
          tailf:info
            "Maximum number of prefixes redistributed to protocol";
          tailf:cli-compact-syntax;
          tailf:cli-sequence-commands;
          leaf number {
            tailf:cli-drop-node-name;
            type uint32 {
              range "1 .. 4294967295";
              tailf:info
                "<1-4294967295>;;Maximum number of IP prefixes redistributed";
            }
          }
          leaf threshold-value {
            tailf:cli-drop-node-name;
            tailf:cli-break-sequence-commands;
            type uint32 {
              range "1 .. 100";
              tailf:info
                "<1-100>;;Threshold value (%) at which to generate a warning message";
            }
          }
          leaf warning-only {
            tailf:info
              "Only give warning message when limit is exceeded";
            tailf:cli-full-command;
            type empty;
          }
          leaf withdraw {
            tailf:info
              "Withdraw redistibuted prefixes";
            tailf:cli-full-command;
            type empty;
          }
        }
        container mobile {
          tailf:info
            "Mobile routes";
          presence "Mobile routes";
          uses ncs_rpc_notif_isis-redist-grouping;
        }
        container odr {
          tailf:info
            "On Demand stub Routes";
          presence "On Demand stub Routes";
          uses ncs_rpc_notif_isis-redist-grouping;
        }
        list ospf {
          tailf:info
            "Open Shortest Path First (OSPF)";
          tailf:cli-suppress-mode;
          tailf:cli-delete-when-empty;
          key "process-id";
          leaf process-id {
            tailf:cli-suppress-range;
            type uint32 {
              range "1 .. 65535";
              tailf:info
                "<1-65535>;;Process ID";
            }
          }
          uses ncs_rpc_notif_isis-redist-grouping;
          container match {
            tailf:cli-compact-syntax;
            tailf:cli-flatten-container;
            tailf:info
              "Redistribution of OSPF routes";
            container internal {
              presence "Redistribute OSPF internal routes";
              tailf:info
                "Redistribute OSPF internal routes";
              tailf:cli-compact-syntax;
              tailf:cli-flatten-container;
              uses ncs_rpc_notif_isis-redist-ospf-match-grouping;
            }
            container external {
              tailf:info
                "Redistribute OSPF external routes";
              presence "Redistribute OSPF external routes";
              tailf:cli-compact-syntax;
              tailf:cli-flatten-container;
              leaf external-routes {
                tailf:cli-drop-node-name;
                type ncs_rpc_notif_redist-ospf-external-type;
              }
              uses ncs_rpc_notif_isis-redist-ospf-match-grouping;
            }
            container nssa-external {
              tailf:info
                "Redistribute OSPF NSSA external routes";
              presence "Redistribute OSPF NSSA external routes";
              tailf:cli-compact-syntax;
              tailf:cli-flatten-container;
              leaf nssa-external-routes {
                tailf:cli-drop-node-name;
                type ncs_rpc_notif_redist-ospf-external-type;
              }
              uses ncs_rpc_notif_isis-redist-ospf-match-grouping;
            }
          }
          leaf vrf {
            tailf:info
              "VPN Routing/Forwarding Instance";
            tailf:cli-diff-dependency "/ios:ip/vrf" {
              tailf:xpath-root 3;
            }
            tailf:cli-diff-dependency "/ios:vrf/definition" {
              tailf:xpath-root 3;
            }
            type string {
              tailf:info
                "WORD;;VPN Routing/Forwarding Instance (VRF) name";
            }
          }
        }
        container rip {
          tailf:info
            "Routing Information Protocol (RIP)";
          presence "Routing Information Protocol (RIP)";
          uses ncs_rpc_notif_isis-redist-grouping;
        }
        container static {
          tailf:info
            "Static routes";
          presence "Static routes";
          uses ncs_rpc_notif_isis-redist-clns-ip-grouping;
        }
      }
      container set-attached-bit {
        tailf:info
          "Conditionally advertise us as attached to L2";
        leaf route-map {
          tailf:info
            "Route-map reference";
          type string {
            tailf:info
              "WORD;;Route map name";
          }
        }
      }
      list summary-address {
        tailf:info
          "Configure IP address summaries";
        tailf:cli-suppress-mode;
        tailf:cli-delete-when-empty;
        key "ip mask";
        leaf ip {
          type inet:ipv4-address {
            tailf:info
              "A.B.C.D;;IP summary address";
          }
        }
        leaf mask {
          type inet:ipv4-address {
            tailf:info
              "A.B.C.D;;Summary mask";
          }
        }
        container level-1 {
          tailf:info
            "Summarize into level-1 area";
          presence "Summarize into level-1 area";
          tailf:cli-compact-syntax;
          uses ncs_rpc_notif_summary-address-metric-tag-grouping;
        }
        container level-1-2 {
          tailf:info
            "Summarize into both area and sub-domain";
          presence "Summarize into both area and sub-domain";
          tailf:cli-compact-syntax;
          uses ncs_rpc_notif_summary-address-metric-tag-grouping;
        }
        container level-2 {
          tailf:info
            "Summarize into level-2 sub-domain";
          presence "Summarize into level-2 sub-domain";
          tailf:cli-compact-syntax;
          uses ncs_rpc_notif_summary-address-metric-tag-grouping;
        }
        container metric-tag-container {
          tailf:cli-drop-node-name;
          tailf:cli-compact-syntax;
          uses ncs_rpc_notif_summary-address-metric-tag-grouping;
        }
      }
      leaf update-queue-depth {
        tailf:info
          "Set Update process queue depth";
        type uint32 {
          range "1 .. 2147483647";
          tailf:info
            "<1-2147483647>;;Max queue depth";
        }
      }
      container use {
        tailf:info
          "Use different algorithms during SPF";
        leaf external-metrics {
          tailf:info
            "Honour external metrics during SPF";
          type empty;
        }
      }
    }
  }

  grouping ncs_rpc_notif_interface-switch-grouping {
    container switchport-conf {
      tailf:cli-no-keyword;
      tailf:cli-drop-node-name;
      leaf switchport {
        tailf:cli-boolean-no;
        type boolean;
      }
    }
    container switchport {
      tailf:info
        "Set switching mode characteristics";
      tailf:cli-incomplete-no;
      container access {
        tailf:info
          "Set access mode characteristics of the interface";
        leaf vlan {
          tailf:info
            "Set VLAN when interface is in access mode";
          tailf:cli-diff-dependency "/ios:vlan/vlan-list/id" {
            tailf:xpath-root 3;
          }
          type union {
            type uint16 {
              tailf:info
                "<1-4094>;;VLAN ID of the VLAN when this port is in access mode";
              range "1..4094";
            }
            type enumeration {
              enum "dynamic" {
                tailf:info
                  "When in access mode, this interfaces VLAN is controlled by VMPS";
              }
            }
          }
        }
      }
      container block {
        tailf:info
          "Disable forwarding of unknown uni/multi cast addresses";
        leaf multicast {
          tailf:info
            "Block unknown multicast addresses";
          tailf:cli-full-command;
          type empty;
        }
        leaf unicast {
          tailf:cli-full-command;
          tailf:info
            "Block unknown unicast addresses";
          type empty;
        }
      }
      container mode {
        tailf:info
          "Set trunking mode of the interface";
        choice mode-choice {
          container access {
            presence "true";
            tailf:info
              "Set trunking mode to ACCESS unconditionally";
          }
          container dot1q-tunnel {
            presence "true";
            tailf:info
              "set trunking mode to TUNNEL unconditionally";
          }
          leaf dynamic {
            tailf:info
              "Set trunking mode to dynamically negotiate access or trunk mode";
            type enumeration {
              enum "auto" {
                tailf:info
                  "Set trunking mode dynamic negotiation parameter to AUTO";
              }
              enum "desirable" {
                tailf:info
                  "Set trunking mode dynamic negotiation parameter to DESIRABLE";
              }
            }
          }
          container trunk {
            presence "true";
            tailf:info
              "Set trunking mode to TRUNK unconditionally";
          }
        }
      }
      leaf nonegotiate {
        tailf:info
          "Device will not engage in negotiation protocol on this interface";
        type empty;
      }
      container port-security {
        tailf:info
          "Security related command";
        presence "true";
        container aging {
          tailf:info
            "Port-security aging commands";
          leaf time {
            tailf:info
              "Port-security aging time";
            type uint16 {
              tailf:info
                "<1-1440>;;Aging time in minutes. Enter a value between 1 and 1440";
              range "1..1440";
            }
          }
          leaf type {
            tailf:info
              "Port-security aging type";
            type enumeration {
              enum "absolute" {
                tailf:info
                  "Absolute aging (default)";
              }
              enum "inactivity" {
                tailf:info
                  "Aging based on inactivity time period";
              }
            }
          }
        }
        container mac-address {
          tailf:info
            "Secure mac address";
          tailf:cli-sequence-commands {
            tailf:cli-reset-siblings;
          }
          tailf:cli-compact-syntax;
          leaf sticky {
            tailf:info
              "Configure dynamic secure addresses as sticky";
            tailf:cli-optional-in-sequence;
            type empty;
          }
          leaf hw-address {
            tailf:cli-drop-node-name;
            type yang:mac-address {
              tailf:info
                "H.H.H;;48 bit mac address";
            }
          }
          leaf vlan {
            tailf:info
              "set VLAN ID of the VLAN on which this address can be learned";
            type uint16 {
              tailf:info
                "<1-4094>;;VLAN ID on which this address can be learned";
              range "1..4094";
            }
          }
        }
        container maximum {
          tailf:info
            "Max secure addresses";
          tailf:cli-sequence-commands {
            tailf:cli-reset-siblings;
          }
          tailf:cli-compact-syntax;
          leaf max-addresses {
            tailf:cli-drop-node-name;
            type uint16 {
              tailf:info
                "<1-4097>;;Maximum addresses";
              range "1..4097";
            }
          }
          leaf vlan {
            tailf:info
              "Max secure addresses per vlan";
            type string {
              tailf:info
                "WORD;;VLAN IDs to which this maximum applies";
            }
          }
        }
        leaf violation {
          tailf:info
            "Security violation mode";
          type enumeration {
            enum "protect" {
              tailf:info
                "Security violation protect mode";
            }
            enum "restrict" {
              tailf:info
                "Security violation restrict mode";
            }
            enum "shutdown" {
              tailf:info
                "Security violation shutdown mode";
            }
          }
        }
      }
      container trunk {
        tailf:info
          "Set trunking characteristics of the interface";
        container allowed {
          tailf:info
            "Set allowed VLAN characteristics when interface is in trunking mode";
          container vlan {
            tailf:info
              "Set allowed VLANs when interface is in trunking mode";
            choice vlan-choice {
              leaf-list vlans {
                tailf:cli-replace-all;
                tailf:cli-range-list-syntax;
                tailf:cli-drop-node-name;
                type uint16 {
                  tailf:info
                    "WORD;;VLAN IDs of the allowed VLANs when this port is in trunking mode";
                }
              }
              leaf all {
                tailf:info
                  "all VLANs";
                type empty;
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
        leaf encapsulation {
          tailf:info
            "Set encapsulation format on trunk port";
          type enumeration {
            enum "dot1q";
            enum "isl";
            enum "negotiate";
          }
        }
        container native {
          tailf:info
            "Set trunking native characteristics when interface is in trunking mode";
          leaf vlan {
            tailf:info
              "Set native VLAN when interface is in trunking mode";
            type union {
              type enumeration {
                enum "tag" {
                  tailf:info
                    "Set native VLAN tagging state";
                }
              }
              type uint16 {
                tailf:info
                  "<1-4094>;;VLAN ID of the native VLAN when this port is in trunking mode";
                range "1..4094";
              }
            }
          }
        }
        container pruning {
          tailf:info
            "Set pruning VLAN characteristics when interface is in trunking mode";
          container vlan {
            tailf:info
              "Set VLANs enabled for pruning when interface is in trunking mode";
            choice vlan-choice {
              leaf-list vlans {
                tailf:cli-range-list-syntax;
                tailf:cli-drop-node-name;
                type uint16 {
                  tailf:info
                    "WORD;;VLAN IDs of the allowed VLANs when this port is in trunking mode";
                }
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
      }
      container voice {
        tailf:info
          "Voice appliance attributes";
        leaf vlan {
          tailf:info
            "Vlan for voice traffic";
          type union {
            type enumeration {
              enum "dot1p" {
                tailf:info
                  "Priority tagged on PVID";
              }
              enum "none" {
                tailf:info
                  "Don't tell telephone about voice vlan";
              }
              enum "untagged" {
                tailf:info
                  "Untagged on PVID";
              }
            }
            type uint16 {
              tailf:info
                "<1-4094>;;Vlan for voice traffic";
              range "1..4094";
            }
          }
        }
        container detect {
          tailf:info
            "detection enhancement keyword";
          tailf:cli-incomplete-command;
          container cisco-phone {
            tailf:info
              "Cisco IP phone";
            presence "true";
            leaf full-duplex {
              tailf:info
                "full duplex keyword";
              type empty;
            }
          }
        }
      }
      container priority {
        tailf:info
          "Set appliance 802.1p priority";
        tailf:cli-incomplete-command;
        container extend {
          tailf:info
            "Set appliance 802.1p priority";
          tailf:cli-incomplete-command;
          choice trust-choice {
            leaf trust {
              tailf:cli-full-command;
              tailf:info
                "Trust 802.1p priorities of devices on appliance";
              type empty;
            }
            leaf cos {
              tailf:info
                "Override 802.1p priority of devices on appliance";
              tailf:cli-full-command;
              type uint8 {
                tailf:info
                  "<0-7>;;Priority for devices on appliance";
                range "0..7";
              }
            }
          }
        }
      }
      container autostate {
        tailf:info
          "Include or exclude this port from vlan link up calculation";
        tailf:cli-incomplete-command;
        leaf exclude {
          tailf:info
            "Exclude this port from vlan link up calculation";
          type empty;
        }
      }
      leaf protected {
        tailf:info
          "Configure an interface to be a protected port";
        type empty;
      }
      leaf host {
        tailf:info
          "Set port host";
        type empty;
      }
    }
    container spanning-tree {
      tailf:info
        "Spanning Tree Subsystem";
      leaf bpdufilter {
        tailf:info
          "Don't send or receive BPDUs on this interface";
        type enumeration {
          enum "disable" {
            tailf:info
              "Disable BPDU filtering for this interface";
          }
          enum "enable" {
            tailf:info
              "Enable BPDU filtering for this interface";
          }
        }
      }
      container bpduguard {
        tailf:info
          "Don't accept BPDUs on this interface";
        choice bpduguard-choice {
          leaf disable {
            tailf:info
              "Disable BPDU guard for this interface";
            type empty;
          }
          leaf enable {
            type empty;
            tailf:info
              "Enable BPDU guard for this interface";
          }
        }
      }
      leaf cost {
        tailf:info
          "To set the path cost of the interface";
        tailf:cli-full-command;
        type uint32 {
          range "1..200000000";
        }
      }
      leaf guard {
        tailf:info
          "Change an interface's spanning tree guard mode";
        tailf:cli-full-command;
        type enumeration {
          enum "loop" {
            tailf:info
              "Set guard mode to loop guard on interface";
          }
          enum "none" {
            tailf:info
              "Set guard mode to none";
          }
          enum "root" {
            tailf:info
              "Set guard mode to root guard on interface";
          }
        }
      }
      leaf link-type {
        tailf:info
          "Specify a link type for spanning tree tree protocol use";
        tailf:cli-full-command;
        type enumeration {
          enum "auto" {
            tailf:code-name "link_type_auto";
            tailf:info
              "Determine link type based on media duplex of this interface";
          }
          enum "none" {
            tailf:info
              "Consider the interface as point-to-point";
          }
          enum "point-to-point" {
            tailf:info
              "Consider the interface as point-to-point";
          }
          enum "root" {
            tailf:info
              "Consider the interface as shared";
          }
        }
      }
      container portfast {
        tailf:info
          "Spanning tree portfast options";
        tailf:cli-delete-when-empty;
        presence "true";
        leaf enable {
          tailf:cli-full-command;
          tailf:cli-drop-node-name;
          type enumeration {
            enum "disable" {
              tailf:info
                "Disable portfast for this interface";
            }
          }
        }
        leaf trunk {
          type empty;
        }
      }
      container loopguard {
        tailf:info
          "Spanning tree loopguard options";
        leaf default {
          tailf:info
            "Enable loopguard by default on all ports";
          type empty;
        }
      }
    }
    container srr-queue {
      container bandwidth {
        container shape {
          tailf:cli-compact-syntax;
          tailf:cli-sequence-commands;
          tailf:cli-reset-container;
          leaf weight1 {
            tailf:cli-drop-node-name;
            tailf:cli-incomplete-command;
            type uint16;
          }
          leaf weight2 {
            tailf:cli-drop-node-name;
            tailf:cli-incomplete-command;
            type uint16;
          }
          leaf weight3 {
            tailf:cli-drop-node-name;
            tailf:cli-incomplete-command;
            type uint16;
          }
          leaf weight4 {
            tailf:cli-drop-node-name;
            type uint16;
          }
        }
        container share {
          tailf:cli-compact-syntax;
          tailf:cli-sequence-commands;
          tailf:cli-reset-container;
          leaf weight1 {
            tailf:cli-drop-node-name;
            tailf:cli-incomplete-command;
            type uint8 {
              range "1..255";
            }
          }
          leaf weight2 {
            tailf:cli-drop-node-name;
            tailf:cli-incomplete-command;
            type uint8 {
              range "1..255";
            }
          }
          leaf weight3 {
            tailf:cli-drop-node-name;
            tailf:cli-incomplete-command;
            type uint8 {
              range "1..255";
            }
          }
          leaf weight4 {
            tailf:cli-drop-node-name;
            type uint8 {
              range "1..255";
            }
          }
        }
      }
    }
  }

  grouping ncs_rpc_notif_password-07-grouping {
    leaf level {
      tailf:info
        "Set exec level password";
      tailf:cli-optional-in-sequence;
      type uint8 {
        tailf:info
          "<1-15>;;Level number";
      }
    }
    leaf type {
      tailf:cli-drop-node-name;
      tailf:cli-optional-in-sequence;
      type enumeration {
        enum "0" {
          tailf:info
            "Specifies an UNENCRYPTED password will follow";
        }
        enum "7" {
          tailf:info
            "Specifies a HIDDEN password will follow";
        }
      }
    }
    leaf secret {
      tailf:cli-drop-node-name;
      type string {
        tailf:info
          "LINE;;The UNENCRYPTED (cleartext) password";
      }
    }
  }

  grouping ncs_rpc_notif_aaa-authentication-dot1x-grouping {
    leaf group {
      tailf:info
        "Use Server-group";
      type union {
        type string {
          tailf:info
            "Server-group name";
        }
        type enumeration {
          enum "radius" {
            tailf:info
              "Use list of all Radius hosts.";
          }
          enum "tacacs+" {
            tailf:info
              "Use list of all Tacacs+ hosts.";
          }
        }
      }
    }
  }

  grouping vrf-route-target-grouping {
    list export {
      tailf:info
        "Export Target-VPN community";
      tailf:cli-suppress-mode;
      tailf:cli-delete-when-empty;
      key "asn-ip";
      leaf asn-ip {
        type asn-ip-type {
          tailf:info
            "ASN:nn or IP-address:nn;;Target VPN Extended Community";
        }
      }
    }
    list import {
      tailf:info
        "Import Target-VPN community";
      tailf:cli-suppress-mode;
      tailf:cli-delete-when-empty;
      key "asn-ip";
      leaf asn-ip {
        type asn-ip-type {
          tailf:info
            "ASN:nn or IP-address:nn;;Target VPN Extended Community";
        }
      }
    }
  }

  grouping police-action-transmit-grouping {
    leaf transmit {
      tailf:info
        "transmit packet";
      type empty;
    }
  }

  grouping police-action-drop-grouping {
    leaf drop {
      tailf:info
        "drop packet";
      type empty;
    }
  }

  grouping police-conform-action-grouping {
    container conform-set-clp-transmit {
      tailf:cli-no-keyword;
      tailf:cli-drop-node-name;
      tailf:cli-flatten-container;
      container conform-action {
        tailf:info
          "action when rate is less than conform burst";
        tailf:cli-flatten-container;
        leaf set-clp-transmit {
          tailf:info
            "set atm clp and send it";
          type empty;
        }
      }
    }
    container conform-set-cos-transmit {
      tailf:cli-no-keyword;
      tailf:cli-drop-node-name;
      tailf:cli-flatten-container;
      container conform-action {
        tailf:info
          "action when rate is less than conform burst";
        tailf:cli-flatten-container;
        leaf set-cos-transmit {
          tailf:info
            "rewrite packet cos and send it";
          type cos_value-type;
        }
      }
    }
    container conform-set-cos-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-cos-transmit {
          tailf:info
            "rewrite packet cos and send it";
          type cos_value-type;
        }
        leaf table {
          tailf:info
            "Specify table-map";
          type leafref {
            path "/ncs:devices/ncs:device/ncs:config/ios:table-map/name" {
              tailf:xpath-root 3;
            }
          }
        }
      }
    }
    container conform-set-discard-class-transmit {
      tailf:cli-no-keyword;
      tailf:cli-drop-node-name;
      tailf:cli-flatten-container;
      container conform-action {
        tailf:info
          "action when rate is less than conform burst";
        tailf:cli-flatten-container;
        leaf set-discard-class-transmit {
          tailf:info
            "set discard-class and send it";
          type uint8 {
            tailf:info
              "<0-7>;;new discard-class";
            range "0..7";
          }
        }
      }
    }
    container conform-set-dscp-transmit {
      tailf:cli-no-keyword;
      tailf:cli-drop-node-name;
      tailf:cli-flatten-container;
      container conform-action {
        tailf:info
          "action when rate is less than conform burst";
        tailf:cli-flatten-container;
        leaf set-dscp-transmit {
          tailf:info
            "set dscp and send it";
          type dscp-type;
        }
      }
    }
    container conform-set-dscp-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-dscp-transmit {
          tailf:info
            "set dscp and send it";
          type dscp-type;
        }
        leaf table {
          tailf:info
            "Specify table-map";
          type leafref {
            path "/ncs:devices/ncs:device/ncs:config/ios:table-map/name" {
              tailf:xpath-root 3;
            }
          }
        }
      }
    }
    container conform-set-frde-transmit {
      tailf:cli-no-keyword;
      tailf:cli-drop-node-name;
      tailf:cli-flatten-container;
      container conform-action {
        tailf:info
          "action when rate is less than conform burst";
        tailf:cli-flatten-container;
        leaf set-frde-transmit {
          tailf:info
            "set FR DE and send it";
          type empty;
        }
      }
    }
    container conform-set-mpls-exp-imposition-transmit {
      tailf:cli-no-keyword;
      tailf:cli-drop-node-name;
      tailf:cli-flatten-container;
      container conform-action {
        tailf:info
          "action when rate is less than conform burst";
        tailf:cli-flatten-container;
        leaf set-mpls-exp-imposition-transmit {
          tailf:info
            "set exp at tag imposition and send it";
          type exp_value-type;
        }
      }
    }
    container conform-set-mpls-exp-imposition-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-mpls-exp-imposition-transmit {
          tailf:info
            "set exp at tag imposition and send it";
          type exp_value-type;
        }
        leaf table {
          tailf:info
            "Specify table-map";
          type leafref {
            path "/ncs:devices/ncs:device/ncs:config/ios:table-map/name" {
              tailf:xpath-root 3;
            }
          }
        }
      }
    }
    container conform-set-mpls-exp-topmost-transmit {
      tailf:cli-no-keyword;
      tailf:cli-drop-node-name;
      tailf:cli-flatten-container;
      container conform-action {
        tailf:info
          "action when rate is less than conform burst";
        tailf:cli-flatten-container;
        leaf set-mpls-exp-topmost-transmit {
          tailf:info
            "set exp on topmost label and send it";
          type exp_value-type;
        }
      }
    }
    container conform-set-mpls-exp-topmost-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-mpls-exp-topmost-transmit {
          tailf:info
            "set exp on topmost label and send it";
          type exp_value-type;
        }
        leaf table {
          tailf:info
            "Specify table-map";
          type leafref {
            path "/ncs:devices/ncs:device/ncs:config/ios:table-map/name" {
              tailf:xpath-root 3;
            }
          }
        }
      }
    }
    container conform-set-prec-transmit {
      tailf:cli-no-keyword;
      tailf:cli-drop-node-name;
      tailf:cli-flatten-container;
      container conform-action {
        tailf:info
          "action when rate is less than conform burst";
        tailf:cli-flatten-container;
        leaf set-prec-transmit {
          tailf:info
            "rewrite packet precedence and send it";
          type prec_value-type;
        }
      }
    }
    container conform-set-prec-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-prec-transmit {
          tailf:info
            "rewrite packet precedence and send it";
          type prec_value-type;
        }
        leaf table {
          tailf:info
            "Specify table-map";
          type leafref {
            path "/ncs:devices/ncs:device/ncs:config/ios:table-map/name" {
              tailf:xpath-root 3;
            }
          }
        }
      }
    }
    container conform-set-qos-transmit {
      tailf:cli-no-keyword;
      tailf:cli-drop-node-name;
      tailf:cli-flatten-container;
      container conform-action {
        tailf:info
          "action when rate is less than conform burst";
        tailf:cli-flatten-container;
        leaf set-qos-transmit {
          tailf:info
            "set qos-group and send it";
          type qos_value-type;
        }
      }
    }
    container conform-set-qos-transmit-table {
      tailf:cli-no-keyword;
      tailf:cli-drop-node-name;
      tailf:cli-flatten-container;
      container conform-action {
        tailf:info
          "action when rate is less than conform burst";
        tailf:cli-compact-syntax;
        tailf:cli-flatten-container;
        tailf:cli-sequence-commands;
        leaf set-qos-transmit {
          tailf:info
            "set qos-group and send it";
          type qos_value-type;
        }
        leaf table {
          tailf:info
            "Specify table-map";
          type leafref {
            path "/ncs:devices/ncs:device/ncs:config/ios:table-map/name" {
              tailf:xpath-root 3;
            }
          }
        }
      }
    }
    container conform-transmit {
      tailf:cli-no-keyword;
      tailf:cli-drop-node-name;
      tailf:cli-flatten-container;
      container conform-action {
        tailf:info
          "action when rate is less than conform burst";
        tailf:cli-flatten-container;
        uses police-action-transmit-grouping;
      }
    }
    container conform-drop {
      tailf:cli-no-keyword;
      tailf:cli-drop-node-name;
      tailf:cli-flatten-container;
      container conform-action {
        tailf:info
          "action when rate is less than conform burst";
        tailf:cli-flatten-container;
        uses police-action-drop-grouping;
      }
    }
  }

  grouping police-exceed-action-grouping {
    container exceed-dscp {
      tailf:cli-no-keyword;
      tailf:cli-drop-node-name;
      tailf:cli-flatten-container;
      container exceed-action {
        tailf:info
          "action when rate is within conform and conform + exceed burst";
        tailf:cli-flatten-container;
        leaf dscp {
          type dscp-type;
        }
      }
    }
    container exceed-set-clp-transmit {
      tailf:cli-no-keyword;
      tailf:cli-drop-node-name;
      tailf:cli-flatten-container;
      container exceed-action {
        tailf:info
          "action when rate is within conform and conform + exceed burst";
        tailf:cli-flatten-container;
        leaf set-clp-transmit {
          tailf:info
            "set atm clp and send it";
          type empty;
        }
      }
    }
    container exceed-set-cos-transmit {
      tailf:cli-no-keyword;
      tailf:cli-drop-node-name;
      tailf:cli-flatten-container;
      container exceed-action {
        tailf:info
          "action when rate is within conform and conform + exceed burst";
        tailf:cli-flatten-container;
        leaf set-cos-transmit {
          tailf:info
            "rewrite packet cos and send it";
          type cos_value-type;
        }
      }
    }
    container exceed-set-discard-class-transmit {
      tailf:cli-no-keyword;
      tailf:cli-drop-node-name;
      tailf:cli-flatten-container;
      container exceed-action {
        tailf:info
          "action when rate is within conform and conform + exceed burst";
        tailf:cli-flatten-container;
        leaf set-discard-class-transmit {
          tailf:info
            "set discard-class and send it";
          type uint8 {
            tailf:info
              "<0-7>;;new discard-class";
            range "0..7";
          }
        }
      }
    }
    container exceed-set-dscp-transmit {
      tailf:cli-no-keyword;
      tailf:cli-drop-node-name;
      tailf:cli-flatten-container;
      container exceed-action {
        tailf:info
          "action when rate is within conform and conform + exceed burst";
        tailf:cli-flatten-container;
        leaf set-dscp-transmit {
          tailf:info
            "set dscp and send it";
          type dscp-type;
        }
      }
    }
    container exceed-set-frde-transmit {
      tailf:cli-no-keyword;
      tailf:cli-drop-node-name;
      tailf:cli-flatten-container;
      container exceed-action {
        tailf:info
          "action when rate is within conform and conform + exceed burst";
        tailf:cli-flatten-container;
        leaf set-frde-transmit {
          tailf:info
            "set FR DE and send it";
          type empty;
        }
      }
    }
    container exceed-set-mpls-exp-imposition-transmit {
      tailf:cli-no-keyword;
      tailf:cli-drop-node-name;
      tailf:cli-flatten-container;
      container exceed-action {
        tailf:info
          "action when rate is within conform and conform + exceed burst";
        tailf:cli-flatten-container;
        leaf set-mpls-exp-imposition-transmit {
          tailf:info
            "set exp at tag imposition and send it";
          type exp_value-type;
        }
      }
    }
    container exceed-set-mpls-exp-topmost-transmit {
      tailf:cli-no-keyword;
      tailf:cli-drop-node-name;
      tailf:cli-flatten-container;
      container exceed-action {
        tailf:info
          "action when rate is within conform and conform + exceed burst";
        tailf:cli-flatten-container;
        leaf set-mpls-exp-topmost-transmit {
          tailf:info
            "set exp on topmost label and send it";
          type exp_value-type;
        }
      }
    }
    container exceed-set-prec-transmit {
      tailf:cli-no-keyword;
      tailf:cli-drop-node-name;
      tailf:cli-flatten-container;
      container exceed-action {
        tailf:info
          "action when rate is within conform and conform + exceed burst";
        tailf:cli-flatten-container;
        leaf set-prec-transmit {
          tailf:info
            "rewrite packet precedence and send it";
          type prec_value-type;
        }
      }
    }
    container exceed-set-qos-transmit {
      tailf:cli-no-keyword;
      tailf:cli-drop-node-name;
      tailf:cli-flatten-container;
      container exceed-action {
        tailf:info
          "action when rate is within conform and conform + exceed burst";
        tailf:cli-flatten-container;
        leaf set-qos-transmit {
          tailf:info
            "set qos-group and send it";
          type qos_value-type;
        }
      }
    }
    container exceed-transmit {
      tailf:cli-no-keyword;
      tailf:cli-drop-node-name;
      tailf:cli-flatten-container;
      container exceed-action {
        tailf:info
          "action when rate is within conform and conform + exceed burst";
        tailf:cli-flatten-container;
        uses police-action-transmit-grouping;
      }
    }
    container exceed-drop {
      tailf:cli-no-keyword;
      tailf:cli-drop-node-name;
      tailf:cli-flatten-container;
      container exceed-action {
        tailf:info
          "action when rate is within conform and conform + exceed burst";
        tailf:cli-flatten-container;
        uses police-action-drop-grouping;
      }
    }
  }

  grouping police-violate-action-grouping {
    container violate-set-clp-transmit {
      tailf:cli-no-keyword;
      tailf:cli-drop-node-name;
      tailf:cli-flatten-container;
      container violate-action {
        tailf:info
          "action when rate is greater than conform + exceed burst";
        tailf:cli-flatten-container;
        leaf set-clp-transmit {
          tailf:info
            "set atm clp and send it";
          type empty;
        }
      }
    }
    container violate-set-cos-transmit {
      tailf:cli-no-keyword;
      tailf:cli-drop-node-name;
      tailf:cli-flatten-container;
      container violate-action {
        tailf:info
          "action when rate is greater than conform + exceed burst";
        tailf:cli-flatten-container;
        leaf set-cos-transmit {
          tailf:info
            "rewrite packet cos and send it";
          type cos_value-type;
        }
      }
    }
    container violate-set-discard-class-transmit {
      tailf:cli-no-keyword;
      tailf:cli-drop-node-name;
      tailf:cli-flatten-container;
      container violate-action {
        tailf:info
          "action when rate is greater than conform + exceed burst";
        tailf:cli-flatten-container;
        leaf set-discard-class-transmit {
          tailf:info
            "set discard-class and send it";
          type uint8 {
            tailf:info
              "<0-7>;;new discard-class";
            range "0..7";
          }
        }
      }
    }
    container violate-set-dscp-transmit {
      tailf:cli-no-keyword;
      tailf:cli-drop-node-name;
      tailf:cli-flatten-container;
      container violate-action {
        tailf:info
          "action when rate is greater than conform + exceed burst";
        tailf:cli-flatten-container;
        leaf set-dscp-transmit {
          tailf:info
            "set dscp and send it";
          type dscp-type;
        }
      }
    }
    container violate-set-frde-transmit {
      tailf:cli-no-keyword;
      tailf:cli-drop-node-name;
      tailf:cli-flatten-container;
      container violate-action {
        tailf:info
          "action when rate is greater than conform + exceed burst";
        tailf:cli-flatten-container;
        leaf set-frde-transmit {
          tailf:info
            "set FR DE and send it";
          type empty;
        }
      }
    }
    container violate-set-mpls-exp-imposition-transmit {
      tailf:cli-no-keyword;
      tailf:cli-drop-node-name;
      tailf:cli-flatten-container;
      container violate-action {
        tailf:info
          "action when rate is greater than conform + exceed burst";
        tailf:cli-flatten-container;
        leaf set-mpls-exp-imposition-transmit {
          tailf:info
            "set exp at tag imposition and send it";
          type exp_value-type;
        }
      }
    }
    container violate-set-mpls-exp-topmost-transmit {
      tailf:cli-no-keyword;
      tailf:cli-drop-node-name;
      tailf:cli-flatten-container;
      container violate-action {
        tailf:info
          "action when rate is greater than conform + exceed burst";
        tailf:cli-flatten-container;
        leaf set-mpls-exp-topmost-transmit {
          tailf:info
            "set exp on topmost label and send it";
          type exp_value-type;
        }
      }
    }
    container violate-set-prec-transmit {
      tailf:cli-no-keyword;
      tailf:cli-drop-node-name;
      tailf:cli-flatten-container;
      container violate-action {
        tailf:info
          "action when rate is greater than conform + exceed burst";
        tailf:cli-flatten-container;
        leaf set-prec-transmit {
          tailf:info
            "rewrite packet precedence and send it";
          type prec_value-type;
        }
      }
    }
    container violate-set-qos-transmit {
      tailf:cli-no-keyword;
      tailf:cli-drop-node-name;
      tailf:cli-flatten-container;
      container violate-action {
        tailf:info
          "action when rate is greater than conform + exceed burst";
        tailf:cli-flatten-container;
        leaf set-qos-transmit {
          tailf:info
            "set qos-group and send it";
          type qos_value-type;
        }
      }
    }
    container violate-transmit {
      tailf:cli-no-keyword;
      tailf:cli-drop-node-name;
      tailf:cli-flatten-container;
      container violate-action {
        tailf:info
          "action when rate is greater than conform + exceed burst";
        tailf:cli-flatten-container;
        uses police-action-transmit-grouping;
      }
    }
    container violate-drop {
      tailf:cli-no-keyword;
      tailf:cli-drop-node-name;
      tailf:cli-flatten-container;
      container violate-action {
        tailf:info
          "action when rate is greater than conform + exceed burst";
        tailf:cli-flatten-container;
        uses police-action-drop-grouping;
      }
    }
  }

  grouping police-action-grouping {
    container actions {
      tailf:cli-break-sequence-commands;
      tailf:cli-no-keyword;
      tailf:cli-drop-node-name;
      tailf:cli-flatten-container;
      uses police-conform-action-grouping;
      uses police-exceed-action-grouping;
      uses police-violate-action-grouping;
    }
  }

  grouping password-grouping {
    container password-container {
      tailf:cli-compact-syntax;
      tailf:cli-flatten-container;
      tailf:cli-sequence-commands;
      tailf:cli-drop-node-name;
      leaf encryption {
        tailf:cli-drop-node-name;
        tailf:cli-incomplete-command;
        tailf:cli-optional-in-sequence;
        type uint8 {
          range "0..7";
          tailf:info
            "<0-7>;;Encryption type (0 to disable encryption, 7 for proprietary)";
        }
        default "0";
      }
      leaf password {
        tailf:cli-drop-node-name;
        tailf:cli-trim-default;
        type string {
          pattern '([1-680-9a-zA-Z].*)|(0.+)|(7.+)';
          tailf:info
            "LINE;;The password";
        }
      }
    }
  }

  grouping distribute-list-grouping {
    container distribute-list {
      tailf:info
        "Filter networks in routing updates";
      list accesslist {
        tailf:cli-drop-node-name;
        tailf:cli-compact-syntax;
        tailf:cli-suppress-mode;
        tailf:cli-delete-when-empty;
        tailf:cli-suppress-list-no;
        key "in-out";
        leaf in-out {
          type access-list-in-out-type;
        }
      }
      list accesslist-ifname {
        tailf:cli-drop-node-name;
        tailf:cli-compact-syntax;
        tailf:cli-suppress-mode;
        tailf:cli-delete-when-empty;
        tailf:cli-suppress-list-no;
        tailf:cli-diff-dependency "/ios:interface" {
          tailf:xpath-root 3;
        }
        key "in-out interface";
        leaf in-out {
          type access-list-in-out-type;
        }
        leaf interface {
          tailf:cli-expose-key-name;
          tailf:info
            "Interface";
          type string {
            tailf:info
              "WORD;;Interface name";
          }
        }
      }
      list accesslist-prefix-gateway {
        tailf:cli-drop-node-name;
        tailf:cli-compact-syntax;
        tailf:cli-suppress-mode;
        tailf:cli-delete-when-empty;
        tailf:cli-suppress-list-no;
        tailf:cli-sequence-commands;
        key "in-out";
        leaf prefix-gateway {
          tailf:cli-drop-node-name;
          tailf:cli-incomplete-command;
          mandatory true;
          tailf:cli-prefix-key;
          type enumeration {
            enum "prefix" {
              tailf:info
                "Filter prefixes in routing updates";
            }
            enum "gateway" {
              tailf:info
                "Filtering incoming updates based on gateway";
            }
          }
        }
        leaf name {
          tailf:cli-drop-node-name;
          mandatory true;
          tailf:cli-prefix-key;
          tailf:cli-disallow-value "in|out";
          type string {
            tailf:info
              "WORD;;Name of an IP prefix-list";
          }
        }
        leaf in-out {
          type access-list-in-out-type;
        }
      }
      list accesslist-prefix-gateway-ifname {
        tailf:cli-drop-node-name;
        tailf:cli-compact-syntax;
        tailf:cli-suppress-mode;
        tailf:cli-delete-when-empty;
        tailf:cli-suppress-list-no;
        tailf:cli-sequence-commands;
        key "in-out interface";
        leaf prefix-gateway {
          tailf:cli-drop-node-name;
          tailf:cli-incomplete-command;
          mandatory true;
          tailf:cli-prefix-key;
          type enumeration {
            enum "prefix" {
              tailf:info
                "Filter prefixes in routing updates";
            }
            enum "gateway" {
              tailf:info
                "Filtering incoming updates based on gateway";
            }
          }
        }
        leaf name {
          tailf:cli-drop-node-name;
          mandatory true;
          tailf:cli-prefix-key;
          tailf:cli-disallow-value "in|out";
          type string {
            tailf:info
              "WORD;;Name of an IP prefix-list";
          }
        }
        leaf in-out {
          type access-list-in-out-type;
        }
        leaf interface {
          tailf:cli-expose-key-name;
          tailf:info
            "Interface";
          type string {
            tailf:info
              "WORD;;Interface name";
          }
        }
      }
    }
  }

  grouping passive-interface-grouping {
    container passive-interface {
      tailf:info
        "Suppress routing updates on an interface";
      choice passive-interface-choice {
        leaf default {
          tailf:info
            "Suppress routing updates on all interfaces";
          type empty;
        }
        leaf interface {
          tailf:cli-drop-node-name;
          tailf:cli-multi-value;
          type string {
            tailf:info
              "WORD;;Interface name";
          }
        }
      }
    }
    container disable {
      when '../passive-interface/default' {
        tailf:xpath-root 3;
      }
      list passive-interface {
        tailf:cli-suppress-mode;
        tailf:cli-delete-when-empty;
        tailf:cli-compact-syntax;
        key "interface";
        leaf interface {
          tailf:cli-drop-node-name;
          tailf:cli-multi-word-key;
          type string {
            tailf:info
              "WORD;;Interface name";
          }
        }
      }
    }
  }

  grouping interface-grouping {
    choice interface-choice {
      leaf Embedded-Service-Engine {
        tailf:info
          "cisco embedded service engine module";
        tailf:cli-allow-join-with-value {
          tailf:cli-display-joined;
        }
        type string;
        tailf:non-strict-leafref {
          path "/ncs:devices/ncs:device/ncs:config/ios:interface/Embedded-Service-Engine/name" {
            tailf:xpath-root 3;
          }
        }
      }
      leaf FastEthernet {
        tailf:info
          "FastEthernet IEEE 802.3";
        tailf:cli-allow-join-with-value {
          tailf:cli-display-joined;
        }
        type string;
        tailf:non-strict-leafref {
          path "/ncs:devices/ncs:device/ncs:config/ios:interface/FastEthernet/name" {
            tailf:xpath-root 3;
          }
        }
      }
      leaf GigabitEthernet {
        tailf:info
          "GigabitEthernet IEEE 802.3z";
        tailf:cli-allow-join-with-value {
          tailf:cli-display-joined;
        }
        type string;
        tailf:non-strict-leafref {
          path "/ncs:devices/ncs:device/ncs:config/ios:interface/GigabitEthernet/name" {
            tailf:xpath-root 3;
          }
        }
      }
      leaf Loopback {
        tailf:info
          "Loopback interface";
        tailf:cli-allow-join-with-value {
          tailf:cli-display-joined;
        }
        type string;
        tailf:non-strict-leafref {
          path "/ncs:devices/ncs:device/ncs:config/ios:interface/Loopback/name" {
            tailf:xpath-root 3;
          }
        }
      }
      leaf Multilink {
        tailf:info
          "Multilink-group interface";
        tailf:cli-allow-join-with-value {
          tailf:cli-display-joined;
        }
        type uint16;
        tailf:non-strict-leafref {
          path "/ncs:devices/ncs:device/ncs:config/ios:interface/Multilink/name" {
            tailf:xpath-root 3;
          }
        }
      }
      leaf Port-channel {
        tailf:info
          "Ethernet Channel of interfaces";
        tailf:cli-allow-join-with-value {
          tailf:cli-display-joined;
        }
        type uint32;
        tailf:non-strict-leafref {
          path "/ncs:devices/ncs:device/ncs:config/ios:interface/Port-channel/name" {
            tailf:xpath-root 3;
          }
        }
      }
      leaf Serial {
        tailf:info
          "Serial interface";
        tailf:cli-allow-join-with-value {
          tailf:cli-display-joined;
        }
        type string;
        tailf:non-strict-leafref {
          path "/ncs:devices/ncs:device/ncs:config/ios:interface/Serial/name" {
            tailf:xpath-root 3;
          }
        }
      }
      leaf TenGigabitEthernet {
        tailf:info
          "Ten Gigabit Ethernet";
        tailf:cli-allow-join-with-value {
          tailf:cli-display-joined;
        }
        type string;
        tailf:non-strict-leafref {
          path "/ncs:devices/ncs:device/ncs:config/ios:interface/TenGigabitEthernet/name" {
            tailf:xpath-root 3;
          }
        }
      }
      leaf Virtual-Template {
        tailf:info
          "Virtual Template interface";
        tailf:cli-allow-join-with-value {
          tailf:cli-display-joined;
        }
        type uint16 {
          tailf:info
            "<1-4095>;;Virtual-Template interface number";
        }
        tailf:non-strict-leafref {
          path "/ncs:devices/ncs:device/ncs:config/ios:interface/Virtual-Template/name" {
            tailf:xpath-root 3;
          }
        }
      }
      leaf Vlan {
        tailf:info
          "Iosxr Vlans";
        tailf:cli-allow-join-with-value {
          tailf:cli-display-joined;
        }
        type uint16;
        tailf:non-strict-leafref {
          path "/ncs:devices/ncs:device/ncs:config/ios:interface/Vlan/name" {
            tailf:xpath-root 3;
          }
        }
      }
    }
  }

  grouping ethernet-grouping {
    choice ethernet-choice {
      leaf FastEthernet {
        tailf:info
          "FastEthernet IEEE 802.3";
        tailf:cli-allow-join-with-value {
          tailf:cli-display-joined;
        }
        type string;
        tailf:non-strict-leafref {
          path "/ncs:devices/ncs:device/ncs:config/ios:interface/FastEthernet/name" {
            tailf:xpath-root 3;
          }
        }
      }
      leaf GigabitEthernet {
        tailf:info
          "GigabitEthernet IEEE 802.3z";
        tailf:cli-allow-join-with-value {
          tailf:cli-display-joined;
        }
        type string;
        tailf:non-strict-leafref {
          path "/ncs:devices/ncs:device/ncs:config/ios:interface/GigabitEthernet/name" {
            tailf:xpath-root 3;
          }
        }
      }
      leaf Port-channel {
        tailf:info
          "Ethernet Channel of interfaces";
        tailf:cli-allow-join-with-value {
          tailf:cli-display-joined;
        }
        type uint32;
        tailf:non-strict-leafref {
          path "/ncs:devices/ncs:device/ncs:config/ios:interface/Port-channel/name" {
            tailf:xpath-root 3;
          }
        }
      }
      leaf TenGigabitEthernet {
        tailf:info
          "Ten Gigabit Ethernet";
        tailf:cli-allow-join-with-value {
          tailf:cli-display-joined;
        }
        type string;
        tailf:non-strict-leafref {
          path "/ncs:devices/ncs:device/ncs:config/ios:interface/TenGigabitEthernet/name" {
            tailf:xpath-root 3;
          }
        }
      }
    }
  }

  grouping ip-community-list-standard-grouping {
    container deny {
      tailf:info
        "Specify community to reject";
      presence "Specify community to reject";
      list deny-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local\-AS)|(no\-advertise)|(no\-export)|(\d+:\d+)|(\d+))( (internet)|(local\-AS)|(no\-advertise)|(no\-export)|(\d+:\d+)|(\d+))*';
          }
        }
      }
    }
    container permit {
      tailf:info
        "Specify community to accept";
      presence "Specify community to accept";
      list permit-list {
        tailf:cli-drop-node-name;
        tailf:cli-suppress-mode;
        tailf:cli-delete-when-empty;
        key "expr";
        leaf expr {
          tailf:cli-multi-word-key {
            tailf:cli-max-words 10;
          }
          type string {
            tailf:info
              "<1-4294967295>  community number
               aa:nn           community number
               internet        Internet (well-known community)
               local-AS        Do not send outside local AS (well-known community)
               no-advertise    Do not advertise to any peer (well-known community)
               no-export       Do not export to next AS (well-known community)
              ";
            pattern '((internet)|(local-AS)|(no-advertise)|(no-export)|(\d+:\d+)|(\d+))( (internet)|(local-AS)|(no-advertise)|(no-export)|(\d+:\d+)|(\d+))*';
          }
        }
      }
    }
  }

  grouping ip-community-list-expanded-grouping {
    container deny {
      tailf:info
        "Specify community to reject";
      presence "Specify community to reject";
      list deny-list {
        tailf:cli-suppress-mode;
        tailf:cli-delete-when-empty;
        tailf:cli-drop-node-name;
        key "expr";
        leaf expr {
          tailf:info
            "LINE;;An ordered list as a regular-expression";
          tailf:cli-multi-word-key {
            tailf:cli-max-words 10;
          }
          type string;
        }
      }
    }
    container permit {
      tailf:info
        "Specify community to accept";
      presence "Specify community to accept";
      list permit-list {
        tailf:cli-suppress-mode;
        tailf:cli-delete-when-empty;
        tailf:cli-drop-node-name;
        key "expr";
        leaf expr {
          tailf:info
            "LINE;;An ordered list as a regular-expression";
          tailf:cli-multi-word-key {
            tailf:cli-max-words 10;
          }
          type string;
        }
      }
    }
  }

  grouping ip-route-options-grouping {
    leaf metric {
      tailf:cli-drop-node-name;
      tailf:cli-break-sequence-commands;
      type uint8 {
        tailf:info
          "<1-255>;;Distance metric for this route";
        range "1..255";
      }
    }
    leaf global {
      tailf:info
        "Next hop address is global";
      type empty;
    }
    leaf name {
      tailf:info
        "Specify name of the next hop";
      type string {
        tailf:info
          "WORD;;Name of the next hop";
      }
    }
    leaf permanent {
      tailf:info
        "permanent route";
      type empty;
    }
    leaf multicast {
      tailf:info
        "multicast route";
      type empty;
    }
    leaf dhcp {
      tailf:info
        "Default Gateway obtained from DHCP";
      tailf:cli-case-insensitive;
      type empty;
    }
    leaf tag {
      tailf:info
        "Set tag for this route";
      type uint32 {
        tailf:info
          "<1-4294967295>;;Tag value";
        range "1..4294967295";
      }
    }
    leaf track {
      tailf:info
        "Install route depending on tracked item";
      type uint16 {
        tailf:info
          "<1-500>;;tracked object number";
        range "1..500";
      }
    }
  }

  grouping ip-route-grouping {
    list ip-route-interface-forwarding-list {
      tailf:cli-drop-node-name;
      tailf:cli-suppress-mode;
      tailf:cli-delete-when-empty;
      tailf:cli-compact-syntax;
      tailf:cli-sequence-commands {
        tailf:cli-reset-all-siblings;
      }
      key "prefix mask interface forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-diff-dependency "/ios:interface" {
          tailf:xpath-root 3;
        }
        type string {
          tailf:info
            "WORD;;Interface name";
        }
      }
      leaf forwarding-address {
        type union {
          type inet:ipv4-address {
            tailf:info
              "A.B.C.D;;Forwarding router's address";
          }
          type enumeration {
            enum "multicast" {
              tailf:info
                "multicast route";
            }
          }
        }
      }
      uses ip-route-options-grouping;
    }
    list ip-route-forwarding-list {
      tailf:cli-drop-node-name;
      tailf:cli-suppress-mode;
      tailf:cli-delete-when-empty;
      tailf:cli-compact-syntax;
      tailf:cli-sequence-commands {
        tailf:cli-reset-all-siblings;
      }
      key "prefix mask forwarding-address";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf forwarding-address {
        type inet:ipv4-address {
          tailf:info
            "A.B.C.D;;Forwarding router's address";
        }
      }
      uses ip-route-options-grouping;
    }
    list ip-route-interface-list {
      tailf:cli-drop-node-name;
      tailf:cli-suppress-mode;
      tailf:cli-delete-when-empty;
      tailf:cli-compact-syntax;
      tailf:cli-sequence-commands {
        tailf:cli-reset-all-siblings;
      }
      key "prefix mask interface";
      leaf prefix {
        tailf:cli-disallow-value "vrf";
        type inet:ipv4-address {
          tailf:info
            "A.B.C.D;;Destination prefix";
        }
      }
      leaf mask {
        type inet:ipv4-address {
          tailf:info
            "A.B.C.D;;Destination prefix mask";
        }
      }
      leaf interface {
        tailf:cli-diff-dependency "/ios:interface" {
          tailf:xpath-root 3;
        }
        tailf:cli-case-insensitive;
        type union {
          type string {
            tailf:info
              "WORD;;Interface name";
          }
          type enumeration {
            enum "dhcp" {
              tailf:info
                "Default Gateway obtained from DHCP";
            }
          }
        }
      }
      uses ip-route-options-grouping;
    }
  }

  grouping ipv6-route-options-grouping {
    leaf distance {
      tailf:cli-drop-node-name;
      type uint8 {
        tailf:info
          "<1-254>;;Administrative distance";
      }
    }
    choice type-choice {
      leaf multicast {
        tailf:info
          "Route only usable by multicast";
        tailf:cli-full-command;
        type empty;
      }
      leaf unicast {
        tailf:info
          "Route only usable by unicast";
        type empty;
      }
    }
    leaf tag {
      tailf:info
        "Tag value";
      tailf:cli-full-command;
      type uint32 {
        tailf:info
          "<0-4294967295>  Tag value";
      }
    }
  }

  grouping ipv6-route-entry-grouping {
    list ipv6-destination-list {
      tailf:cli-drop-node-name;
      tailf:cli-suppress-mode;
      tailf:cli-delete-when-empty;
      tailf:cli-compact-syntax;
      tailf:cli-reset-container;
      key "destination";
      leaf destination {
        type inet:ipv6-address {
          tailf:info
            "X:X:X:X::X;;IPv6 address of next-hop";
        }
      }
      uses ipv6-route-options-grouping;
    }
  }

  grouping ipv6-route-grouping {
    list ipv6-route-list {
      tailf:cli-drop-node-name;
      tailf:cli-suppress-mode;
      tailf:cli-delete-when-empty;
      tailf:cli-compact-syntax;
      tailf:cli-reset-container;
      tailf:cli-incomplete-command;
      key "prefix";
      leaf prefix {
        type ipv6-prefix {
          tailf:info
            "X:X:X:X::X/<0-128>;;IPv6 prefix x:x::y/<z>";
        }
      }
      uses ipv6-route-entry-grouping;
      list FastEthernet {
        tailf:info
          "FastEthernet IEEE 802.3";
        tailf:cli-allow-join-with-key {
          tailf:cli-display-joined;
        }
        tailf:cli-suppress-mode;
        tailf:cli-delete-when-empty;
        tailf:cli-compact-syntax;
        tailf:cli-reset-container;
        key "name";
        leaf name {
          type string {
            tailf:info
              "<0-66>/<0-128>;;FastEthernet interface number";
          }
        }
        uses ipv6-route-entry-grouping;
        uses ipv6-route-options-grouping;
      }
      list Null {
        tailf:info
          "Null interface";
        tailf:cli-allow-join-with-key {
          tailf:cli-display-joined;
        }
        tailf:cli-suppress-mode;
        tailf:cli-delete-when-empty;
        tailf:cli-compact-syntax;
        tailf:cli-reset-container;
        key "name";
        leaf name {
          type enumeration {
            enum "0" {
              tailf:info
                "<0-0>;;Null interface number";
            }
          }
        }
        uses ipv6-route-entry-grouping;
        uses ipv6-route-options-grouping;
      }
    }
  }

  grouping random-detect-grouping {
    leaf min-threshold {
      tailf:cli-drop-node-name;
      tailf:cli-incomplete-command;
      type uint16 {
        range "1..4096";
        tailf:info
          "<1-4096>;;minimum threshold (number of packets)";
      }
    }
    leaf max-threshold {
      tailf:cli-drop-node-name;
      tailf:cli-incomplete-command;
      type uint16 {
        range "1..4096";
        tailf:info
          "<1-4096>;;maximum threshold (number of packets)";
      }
    }
    leaf denominator {
      tailf:cli-drop-node-name;
      type uint32 {
        range "1..65535";
        tailf:info
          "<1-65535>;;mark probability denominator";
      }
    }
  }

  grouping class-map-match-grouping {
    container access-group {
      tailf:info
        "Access group";
      leaf index {
        tailf:cli-drop-node-name;
        type uint32 {
          range "1..2699" {
            tailf:info
              "<1-2699>;;Access list index";
          }
        }
      }
      leaf-list name {
        tailf:info
          "Named Access List";
        tailf:cli-list-syntax;
        type string {
          tailf:info
            "WORD;;Access List name";
        }
      }
    }
    leaf any {
      tailf:info
        "Any packets";
      type empty;
    }
    leaf-list class-map {
      tailf:info
        "Class map";
      tailf:cli-list-syntax;
      type leafref {
        path "/ncs:devices/ncs:device/ncs:config/ios:class-map/name" {
          tailf:xpath-root 3;
        }
      }
    }
    leaf-list cos {
      tailf:info
        "IEEE 802.1Q/ISL class of service/user priority values";
      tailf:cli-flat-list-syntax;
      type uint16 {
        range "0..7";
        tailf:info
          "<0-7>;;Enter up to 4 class-of-service values separated by white-spaces";
      }
    }
    container destination-address {
      tailf:info
        "Destination address";
      leaf-list mac {
        tailf:info
          "MAC address";
        tailf:cli-list-syntax;
        type string {
          tailf:info
            "H.H.H;;MAC address";
        }
      }
    }
    leaf-list discard-class {
      tailf:info
        "Discard behavior identifier";
      tailf:cli-list-syntax;
      type uint16 {
        range "0..7";
        tailf:info
          "<0-7>;;Discard Class value";
      }
    }
    leaf-list dscp {
      tailf:info
        "Match DSCP in IP(v4) and IPv6 packets";
      tailf:cli-list-syntax;
      type dscp-type;
    }
    leaf fr-de {
      tailf:info
        "Match on Frame-relay DE bit";
      type empty;
    }
    leaf-list fr-dlci {
      tailf:info
        "Match on fr-dlci";
      tailf:cli-list-syntax;
      type uint16 {
        range "16..1007";
        tailf:info
          "<16-1007>;;frame-relay dlci number";
      }
    }
    leaf-list input-interface {
      tailf:info
        "Select an input interface to match";
      tailf:cli-list-syntax;
      type string;
    }
    container ip {
      tailf:info
        "IP specific values";
      leaf-list dscp {
        tailf:info
          "Match IP DSCP (DiffServ CodePoints)";
        tailf:cli-flat-list-syntax;
        type dscp-type;
      }
      leaf-list precedence {
        tailf:info
          "Match IP precedence";
        tailf:cli-flat-list-syntax;
        type precedence-type;
      }
      list rtp {
        tailf:info
          "Match RTP port nos";
        key "port1 port2";
        leaf port1 {
          type uint16 {
            range "2000..65535";
            tailf:info
              "<2000-65535>;;Lower bound of UDP destination port";
          }
        }
        leaf port2 {
          type uint16 {
            range "0..16383";
            tailf:info
              "<0-16383>;;Range of UDP ports";
          }
        }
      }
    }
    container mpls {
      tailf:info
        "Multi Protocol Label Switching specific values";
      container experimental {
        tailf:info
          "Match MPLS experimental";
        leaf-list topmost {
          tailf:info
            "Match MPLS experimental value on topmost label";
          tailf:cli-flat-list-syntax;
          type uint16 {
            range "0..7";
            tailf:info
              "<0-7>;;Enter up to 8 experimental values separated by white-spaces";
          }
        }
      }
    }
    container packet {
      tailf:info
        "Layer 3 Packet length";
      container length {
        tailf:info
          "Layer 3 Packet length";
        leaf max {
          tailf:info
            "Maximum length of packet";
          type uint16 {
            range "1..2000";
            tailf:info
              "<1-2000>;;Packet length in bytes";
          }
        }
        leaf min {
          tailf:info
            "Minimum length of packet";
          type uint16 {
            range "1..2000";
            tailf:info
              "<1-2000>;;Packet length in bytes";
          }
        }
      }
    }
    leaf-list precedence {
      tailf:info
        "Match Precedence in IP(v4) and IPv6 packets";
      tailf:cli-flat-list-syntax;
      type precedence-type;
    }
    container protocol {
      tailf:info
        "Protocol";
      leaf x802-11-iapp {
        tailf:info
          "IEEE 802.11 WLANs WG IAPP";
        tailf:alt-name "802-11-iapp";
        type empty;
      }
      leaf ace-svr {
        tailf:info
          "ACE Server/Propagation";
        type empty;
      }
      leaf aol {
        tailf:info
          "America-Online Instant Messenger";
        type empty;
      }
      leaf appleqtc {
        tailf:info
          "Apple QuickTime";
        type empty;
      }
      leaf biff {
        tailf:info
          "Bliff mail notification";
        type empty;
      }
      leaf bittorrent {
        tailf:info
          "bittorrent";
        type empty;
      }
      leaf bootpc {
        tailf:info
          "Bootstrap Protocol Client";
        type empty;
      }
      leaf bootps {
        tailf:info
          "Bootstrap Protocol Server";
        type empty;
      }
      leaf cddbp {
        tailf:info
          "CD Database Protocol";
        type empty;
      }
      leaf cifs {
        tailf:info
          "CIFS";
        type empty;
      }
      leaf cisco-fna {
        tailf:info
          "Cisco FNATIVE";
        type empty;
      }
      leaf cisco-net-mgmt {
        tailf:info
          "cisco-net-mgmt";
        type empty;
      }
      leaf cisco-svcs {
        tailf:info
          "cisco license/perf/GDP/X.25/ident svcs";
        type empty;
      }
      leaf cisco-sys {
        tailf:info
          "Cisco SYSMAINT";
        type empty;
      }
      leaf cisco-tdp {
        tailf:info
          "Cisco TDP";
        type empty;
      }
      leaf cisco-tna {
        tailf:info
          "Cisco TNATIVE";
        type empty;
      }
      leaf citriximaclient {
        tailf:info
          "Citrix IMA Client";
        type empty;
      }
      leaf clp {
        tailf:info
          "Cisco Line Protocol";
        type empty;
      }
      leaf creativepartnr {
        tailf:info
          "Creative Partnr";
        type empty;
      }
      leaf creativeserver {
        tailf:info
          "Creative Server";
        type empty;
      }
      leaf daytime {
        tailf:info
          "Daytime (RFC 867)";
        type empty;
      }
      leaf dbase {
        tailf:info
          "dBASE Unix";
        type empty;
      }
      leaf dbcontrol_agent {
        tailf:info
          "Oracle dbControl Agent po";
        type empty;
      }
      leaf ddns-v3 {
        tailf:info
          "Dynamic DNS Version 3";
        type empty;
      }
      leaf dhcp-failover {
        tailf:info
          "DHCP Failover";
        type empty;
      }
      leaf directconnect {
        tailf:info
          "Direct Connect Version 2.0";
        type empty;
      }
      leaf discard {
        tailf:info
          "Discard port";
        type empty;
      }
      leaf dnsix {
        tailf:info
          "DNSIX Securit Attribute Token Map";
        type empty;
      }
      leaf echo {
        tailf:info
          "Echo port";
        type empty;
      }
      leaf entrust-svc-hdlr {
        tailf:info
          "Entrust KM/Admin Service Handler";
        type empty;
      }
      leaf entrust-svcs {
        tailf:info
          "Entrust sps/aaas/aams";
        type empty;
      }
      leaf exec {
        tailf:info
          "Remote Process Execution";
        type empty;
      }
      leaf fcip-port {
        tailf:info
          "FCIP";
        type empty;
      }
      leaf ftps {
        tailf:info
          "FTP over TLS/SSL";
        type empty;
      }
      leaf gdoi {
        tailf:info
          "GDOI";
        type empty;
      }
      leaf giop {
        tailf:info
          "Oracle GIOP/SSL";
        type empty;
      }
      leaf gtpv0 {
        tailf:info
          "GPRS Tunneling Protocol Version 0";
        type empty;
      }
      leaf gtpv1 {
        tailf:info
          "GPRS Tunneling Protocol Version 1";
        type empty;
      }
      leaf h225ras {
        tailf:info
          "H225 RAS over Unicast";
        type empty;
      }
      leaf h323callsigalt {
        tailf:info
          "h323 Call Signal Alternate";
        type empty;
      }
      leaf hp-alarm-mgr {
        tailf:info
          "HP Performance data alarm manager";
        type empty;
      }
      leaf hp-collector {
        tailf:info
          "HP Performance data collector";
        type empty;
      }
      leaf hp-managed-node {
        tailf:info
          "HP Performance data managed node";
        type empty;
      }
      leaf hsrp {
        tailf:info
          "Hot Standby Router Protocol";
        type empty;
      }
      leaf https {
        tailf:info
          "Secure Hypertext Transfer Protocol";
        type empty;
      }
      leaf ica {
        tailf:info
          "ica (Citrix)";
        type empty;
      }
      leaf icabrowser {
        tailf:info
          "icabrowser (Citrix)";
        type empty;
      }
      leaf ident {
        tailf:info
          "Authentication Service";
        type empty;
      }
      leaf igmpv3lite {
        tailf:info
          "IGMP over UDP for SSM";
        type empty;
      }
      leaf imap3 {
        tailf:info
          "Interactive Mail Access Protocol 3";
        type empty;
      }
      leaf imaps {
        tailf:info
          "IMAP over TLS/SSL";
        type empty;
      }
      leaf ipass {
        tailf:info
          "IPASS";
        type empty;
      }
      leaf ipsec-msft {
        tailf:info
          "Microsoft IPsec NAT-T";
        type empty;
      }
      leaf irc-serv {
        tailf:info
          "IRC-SERV";
        type empty;
      }
      leaf ircs {
        tailf:info
          "IRC over TLS/SSL";
        type empty;
      }
      leaf ircu {
        tailf:info
          "IRCU";
        type empty;
      }
      leaf isakmp {
        tailf:info
          "ISAKMP";
        type empty;
      }
      leaf iscsi {
        tailf:info
          "iSCSI";
        type empty;
      }
      leaf iscsi-target {
        tailf:info
          "iSCSI port";
        type empty;
      }
      leaf kermit {
        tailf:info
          "kermit";
        type empty;
      }
      leaf ldap-admin {
        tailf:info
          "LDAP admin server port";
        type empty;
      }
      leaf ldaps {
        tailf:info
          "LDAP over TLS/SSL";
        type empty;
      }
      leaf login {
        tailf:info
          "Remote login";
        type empty;
      }
      leaf lotusmtap {
        tailf:info
          "Lotus Mail Tracking Agent Protocol";
        type empty;
      }
      leaf lotusnote {
        tailf:info
          "Lotus Note";
        type empty;
      }
      leaf microsoft-ds {
        tailf:info
          "Microsoft-DS";
        type empty;
      }
      leaf ms-cluster-net {
        tailf:info
          "MS Cluster Net";
        type empty;
      }
      leaf ms-dotnetster {
        tailf:info
          "Microsoft .NETster Port";
        type empty;
      }
      leaf ms-sna {
        tailf:info
          "Microsoft SNA Server/Base";
        type empty;
      }
      leaf ms-sql {
        tailf:info
          "Microsoft SQL";
        type empty;
      }
      leaf ms-sql-m {
        tailf:info
          "Microsoft SQL Monitor";
        type empty;
      }
      leaf msexch-routing {
        tailf:info
          "Microsoft Exchange Routing";
        type empty;
      }
      leaf msnmsgr {
        tailf:info
          "MSN Instant Messenger";
        type empty;
      }
      leaf msrpc {
        tailf:info
          "Microsoft Remote Procedure Call";
        type empty;
      }
      leaf mysql {
        tailf:info
          "MySQL";
        type empty;
      }
      leaf n2h2server {
        tailf:info
          "N2H2 Filter Service Port";
        type empty;
      }
      leaf ncp {
        tailf:info
          "NCP (Novell)";
        type empty;
      }
      leaf net8-cman {
        tailf:info
          "Oracle Net8 Cman/Admin";
        type empty;
      }
      leaf netbios-dgm {
        tailf:info
          "NETBIOS Datagram Service";
        type empty;
      }
      leaf netbios-ns {
        tailf:info
          "NETBIOS Name Service";
        type empty;
      }
      leaf netbios-ssn {
        tailf:info
          "NETBIOS Session Service";
        type empty;
      }
      leaf netstat {
        tailf:info
          "Variant of systat";
        type empty;
      }
      leaf oem-agent {
        tailf:info
          "OEM Agent (Oracle)";
        type empty;
      }
      leaf oracle {
        tailf:info
          "Oracle";
        type empty;
      }
      leaf oracle-em-vp {
        tailf:info
          "Oracle EM/VP";
        type empty;
      }
      leaf oraclenames {
        tailf:info
          "Oracle Names";
        type empty;
      }
      leaf orasrv {
        tailf:info
          "Oracle SQL*Net v1/v2";
        type empty;
      }
      leaf pcanywheredata {
        tailf:info
          "pcANYWHEREdata";
        type empty;
      }
      leaf pcanywherestat {
        tailf:info
          "pcANYWHEREstat";
        type empty;
      }
      leaf pop3s {
        tailf:info
          "POP3 over TLS/SSL";
        type empty;
      }
      leaf pwdgen {
        tailf:info
          "Password  Generator Protocol";
        type empty;
      }
      leaf qmtp {
        tailf:info
          "Quick Mail Transfer Protocol";
        type empty;
      }
      leaf r-winsock {
        tailf:info
          "remote-winsock";
        type empty;
      }
      leaf radius {
        tailf:info
          "RADIUS & Accounting";
        type empty;
      }
      leaf rdb-dbs-disp {
        tailf:info
          "Oracle RDB";
        type empty;
      }
      leaf realmedia {
        tailf:info
          "RealNetwork's Realmedia Protocol";
        type empty;
      }
      leaf realsecure {
        tailf:info
          "ISS Real Secure Console Service Port";
        type empty;
      }
      leaf router {
        tailf:info
          "Local Routing Process";
        type empty;
      }
      leaf rsvp-encap {
        tailf:info
          "RSVP ENCAPSULATION-1/2";
        type empty;
      }
      leaf rsvp_tunnel {
        tailf:info
          "RSVP Tunnel";
        type empty;
      }
      leaf rtc-pm-port {
        tailf:info
          "Oracle RTC-PM port";
        type empty;
      }
      leaf rtelnet {
        tailf:info
          "Remote Telnet Service";
        type empty;
      }
      leaf send {
        tailf:info
          "SEND";
        type empty;
      }
      leaf shell {
        tailf:info
          "Remote command";
        type empty;
      }
      leaf sip-tls {
        tailf:info
          "SIP-TLS";
        type empty;
      }
      leaf sms {
        tailf:info
          "SMS RCINFO/XFER/CHAT";
        type empty;
      }
      leaf snmptrap {
        tailf:info
          "SNMP Trap";
        type empty;
      }
      leaf sql-net {
        tailf:info
          "SQL-NET";
        type empty;
      }
      leaf sqlserv {
        tailf:info
          "SQL Services";
        type empty;
      }
      leaf sqlsrv {
        tailf:info
          "SQL Service";
        type empty;
      }
      leaf sshell {
        tailf:info
          "SSLshell";
        type empty;
      }
      leaf ssp {
        tailf:info
          "State Sync Protocol";
        type empty;
      }
      leaf syslog-conn {
        tailf:info
          "Reliable Syslog Service";
        type empty;
      }
      leaf tacacs {
        tailf:info
          "Login Host Protocol (TACACS)";
        type empty;
      }
      leaf tacacs-ds {
        tailf:info
          "TACACS-Database Service";
        type empty;
      }
      leaf tarantella {
        tailf:info
          "Tarantella";
        type empty;
      }
      leaf tcp {
        tailf:info
          "TCP";
        type empty;
      }
      leaf telnets {
        tailf:info
          "Telnet over TLS/SSL";
        type empty;
      }
      leaf time {
        tailf:info
          "Time";
        type empty;
      }
      leaf timed {
        tailf:info
          "Time server";
        type empty;
      }
      leaf tr-rsrb {
        tailf:info
          "cisco RSRB";
        type empty;
      }
      leaf ttc {
        tailf:info
          "Oracle TTC/SSL";
        type empty;
      }
      leaf udp {
        tailf:info
          "UDP";
        type empty;
      }
      leaf uucp {
        tailf:info
          "UUCPD/UUCP-RLOGIN";
        type empty;
      }
      leaf vqp {
        tailf:info
          "VQP";
        type empty;
      }
      leaf webster {
        tailf:info
          "Network Disctionary";
        type empty;
      }
      leaf who {
        tailf:info
          "Who's service";
        type empty;
      }
      leaf wins {
        tailf:info
          "Microsoft WINS";
        type empty;
      }
      leaf x11 {
        tailf:info
          "X Window System";
        type empty;
      }
      leaf xdmcp {
        tailf:info
          "XDM Control Protocol";
        type empty;
      }
      leaf ymsgr {
        tailf:info
          "Yahoo! Instant Messenger";
        type empty;
      }
      leaf aarp {
        tailf:info
          "AppleTalk ARP";
        type empty;
      }
      leaf appletalk {
        tailf:info
          "AppleTalk";
        type empty;
      }
      leaf arp {
        tailf:info
          "IP ARP";
        type empty;
      }
      leaf bgp {
        tailf:info
          "Border Gateway Protocol";
        type empty;
      }
      leaf bridge {
        tailf:info
          "Bridging";
        type empty;
      }
      leaf bstun {
        tailf:info
          "Block Serial Tunnel";
        type empty;
      }
      leaf cdp {
        tailf:info
          "Cisco Discovery Protocol";
        type empty;
      }
      container citrix {
        tailf:info
          "Citrix Systems ICA protocol";
        presence "enable citrix system protocol matching";
        leaf ica-tag {
          tailf:info
            "Citrix ICA tag 0-high 1-medium 2-low 3-background";
          type string {
            tailf:info
              "WORD;;Enter a string as the sub-protocol parameter";
          }
        }
      }
      leaf clns {
        tailf:info
          "ISO CLNS";
        type empty;
      }
      leaf clns_es {
        tailf:info
          "ISO CLNS End System";
        type empty;
      }
      leaf clns_is {
        tailf:info
          "ISO CLNS Intermediate System";
        type empty;
      }
      leaf cmns {
        tailf:info
          "ISO CMNS";
        type empty;
      }
      leaf compressedtcp {
        tailf:info
          "Compressed TCP (VJ";
        type empty;
      }
      leaf cuseeme {
        tailf:info
          "CU-SeeMe desktop video conference";
        type empty;
      }
      leaf decnet {
        tailf:info
          "DECnet";
        type empty;
      }
      leaf decnet_node {
        tailf:info
          "DECnet Node";
        type empty;
      }
      leaf decnet_router-l1 {
        tailf:info
          "DECnet Router L1";
        type empty;
      }
      leaf decnet_router-l2 {
        tailf:info
          "DECnet Router L2";
        type empty;
      }
      leaf dhcp {
        tailf:info
          "Dynamic Host Configuration";
        type empty;
      }
      leaf dlsw {
        type empty;
        tailf:info
          "Data Link Switching (Direct encapsulation only";
      }
      leaf dns {
        type empty;
        tailf:info
          "Domain Name Server lookup";
      }
      leaf edonkey {
        type empty;
        tailf:info
          "eDonkey";
      }
      leaf egp {
        type empty;
        tailf:info
          "Exterior Gateway Protocol";
      }
      leaf eigrp {
        type empty;
        tailf:info
          "Enhanced Interior Gateway Routing Protocol";
      }
      leaf exchange {
        type empty;
        tailf:info
          "MS-RPC for Exchange";
      }
      container fasttrack {
        tailf:info
          "FastTrack Traffic - KaZaA, Morpheus, Grokster";
        presence "enable fasttrack matching";
        leaf file-transfer {
          tailf:info
            "File transfer stream";
          type string {
            tailf:info
              "WORD;;Enter a string as the sub-protocol parameter";
          }
        }
      }
      leaf finger {
        type empty;
        tailf:info
          "Finger";
      }
      leaf ftp {
        type empty;
        tailf:info
          "File Transfer Protocol";
      }
      container gnutella {
        tailf:info
          "Gnutella Version2 Traffic - BearShare, Shareeza, Morpheus";
        presence "enable gnutella matching";
        leaf file-transfer {
          tailf:info
            "File transfer stream";
          type string {
            tailf:info
              "WORD;;Enter a string as the sub-protocol parameter";
          }
        }
      }
      leaf gopher {
        type empty;
        tailf:info
          "Gopher";
      }
      leaf gre {
        type empty;
        tailf:info
          "Generic Routing Encapsulation";
      }
      leaf h323 {
        type empty;
        tailf:info
          "H323 Protocol";
      }
      container http {
        tailf:info
          "World Wide Web traffic";
        presence "enable http traffic matching";
        leaf c-header-field {
          tailf:info
            "Client general Header Field";
          type string {
            tailf:info
              "WORD;;Enter a string as the sub-protocol parameter";
          }
        }
        leaf host {
          tailf:info
            "Server Host Name";
          type string {
            tailf:info
              "WORD;;Enter a string as the sub-protocol parameter";
          }
        }
        leaf mime {
          tailf:info
            "Match MIME Type";
          type string {
            tailf:info
              "WORD;;Enter a string as the sub-protocol parameter";
          }
        }
        leaf s-header-field {
          tailf:info
            "Server general Header Field";
          type string {
            tailf:info
              "WORD;;Enter a string as the sub-protocol parameter";
          }
        }
        leaf url {
          tailf:info
            "Match URL String";
          type string {
            tailf:info
              "WORD;;Enter a string as the sub-protocol parameter";
          }
        }
      }
      leaf icmp {
        tailf:info
          "Internet Control Message";
        type empty;
      }
      leaf imap {
        tailf:info
          "Internet Message Access Protocol";
        type empty;
      }
      leaf ip {
        tailf:info
          "IP";
        type empty;
      }
      leaf ipinip {
        tailf:info
          "IP in IP (encapsulation";
        type empty;
      }
      leaf ipsec {
        tailf:info
          "IP Security Protocol (ESP/AH";
        type empty;
      }
      leaf ipv6 {
        tailf:info
          "IPV6";
        type empty;
      }
      leaf ipx {
        tailf:info
          "Novell IPX";
        type empty;
      }
      leaf irc {
        type empty;
        tailf:info
          "Internet Relay Chat";
      }
      container kazaa2 {
        tailf:info
          "Kazaa Version 2";
        presence "enable kazaa version 2 matching";
        leaf file-transfer {
          tailf:info
            "File transfer stream";
          type string {
            tailf:info
              "WORD;;Enter a string as the sub-protocol parameter";
          }
        }
      }
      leaf kerberos {
        tailf:info
          "Kerberos";
        type empty;
      }
      leaf l2tp {
        tailf:info
          "L2F/L2TP tunnel";
        type empty;
      }
      leaf ldap {
        tailf:info
          "Lightweight Directory Access Protocol";
        type empty;
      }
      leaf llc2 {
        tailf:info
          "llc2";
        type empty;
      }
      leaf mgcp {
        tailf:info
          "Media Gateway Control Protocol";
        type empty;
      }
      container napster {
        tailf:info
          "Napster Traffic";
        presence "enable napster matching";
        leaf non-std {
          tailf:info
            "Non-standard port advertizements";
          type empty;
        }
      }
      leaf netbios {
        tailf:info
          "NetBIOS";
        type empty;
      }
      leaf netshow {
        tailf:info
          "Microsoft Netshow";
        type empty;
      }
      leaf nfs {
        tailf:info
          "Network File System";
        type empty;
      }
      leaf nntp {
        tailf:info
          "Network News Transfer Protocol";
        type empty;
      }
      leaf notes {
        tailf:info
          "Lotus Notes(R";
        type empty;
      }
      leaf novadigm {
        tailf:info
          "Novadigm EDM";
        type empty;
      }
      leaf ntp {
        tailf:info
          "Network Time Protocol";
        type empty;
      }
      leaf ospf {
        tailf:info
          "Open Shortest Path First";
        type empty;
      }
      leaf pad {
        tailf:info
          "PAD links";
        type empty;
      }
      leaf pcanywhere {
        tailf:info
          "Symantec pcANYWHERE";
        type empty;
      }
      leaf pop3 {
        tailf:info
          "Post Office Protocol";
        type empty;
      }
      leaf pppoe {
        tailf:info
          "PPP over Ethernet";
        type empty;
      }
      leaf pptp {
        tailf:info
          "Point-to-Point Tunneling Protocol";
        type empty;
      }
      leaf printer {
        tailf:info
          "print spooler/lpd";
        type empty;
      }
      leaf qllc {
        tailf:info
          "qllc protocol";
        type empty;
      }
      leaf rcmd {
        tailf:info
          "BSD r-commands (rsh, rlogin, rexec";
        type empty;
      }
      leaf rip {
        tailf:info
          "Routing Information Protocol";
        type empty;
      }
      leaf rsrb {
        tailf:info
          "Remote Source-Route Bridging";
        type empty;
      }
      leaf rsvp {
        tailf:info
          "Resource Reservation Protocol";
        type empty;
      }
      leaf rtcp {
        tailf:info
          "Real Time Control Protocol";
        type empty;
      }
      container rtp {
        tailf:info
          "Real Time Protocol";
        presence "enable rtp matching";
        leaf audio {
          tailf:info
            "Match voice packets";
          type empty;
        }
        leaf payload-type {
          tailf:info
            "Match an explicit PT";
          type string {
            tailf:info
              "WORD;;Enter a string as the sub-protocol parameter";
          }
        }
        leaf video {
          tailf:info
            "Match video packets";
          type empty;
        }
      }
      leaf rtsp {
        tailf:info
          "Real Time Streaming Protocol";
        type empty;
      }
      leaf secure-ftp {
        tailf:info
          "FTP over TLS/SSL";
        type empty;
      }
      leaf secure-http {
        tailf:info
          "Secured HTTP";
        type empty;
      }
      leaf secure-imap {
        tailf:info
          "Internet Message Access Protocol over TLS/SSL";
        type empty;
      }
      leaf secure-irc {
        tailf:info
          "Internet Relay Chat over TLS/SSL";
        type empty;
      }
      leaf secure-ldap {
        tailf:info
          "Lightweight Directory Access Protocol over TLS/SSL";
        type empty;
      }
      leaf secure-nntp {
        tailf:info
          "Network News Transfer Protocol over TLS/SSL";
        type empty;
      }
      leaf secure-pop3 {
        tailf:info
          "Post Office Protocol over TLS/SSL";
        type empty;
      }
      leaf secure-telnet {
        tailf:info
          "Telnet over TLS/SSL";
        type empty;
      }
      leaf sip {
        tailf:info
          "Session Initiation Protocol";
        type empty;
      }
      leaf skinny {
        tailf:info
          "Skinny Protocol";
        type empty;
      }
      leaf smtp {
        tailf:info
          "Simple Mail Transfer Protocol";
        type empty;
      }
      leaf snapshot {
        tailf:info
          "Snapshot routing support";
        type empty;
      }
      leaf snmp {
        tailf:info
          "Simple Network Management Protocol";
        type empty;
      }
      leaf socks {
        tailf:info
          "SOCKS";
        type empty;
      }
      leaf sqlnet {
        tailf:info
          "SQL*NET for Oracle";
        type empty;
      }
      leaf sqlserver {
        tailf:info
          "MS SQL Server";
        type empty;
      }
      leaf ssh {
        tailf:info
          "Secured Shell";
        type empty;
      }
      leaf streamwork {
        tailf:info
          "Xing Technology StreamWorks player";
        type empty;
      }
      leaf stun {
        tailf:info
          "Serial Tunnel";
        type empty;
      }
      leaf sunrpc {
        tailf:info
          "Sun RPC";
        type empty;
      }
      leaf syslog {
        tailf:info
          "System Logging Utility";
        type empty;
      }
      leaf telnet {
        tailf:info
          "Telnet";
        type empty;
      }
      leaf tftp {
        tailf:info
          "Trivial File Transfer Protocol";
        type empty;
      }
      leaf vdolive {
        tailf:info
          "VDOLive streaming video";
        type empty;
      }
      leaf vofr {
        tailf:info
          "voice over Frame Relay packets";
        type empty;
      }
      leaf winmx {
        tailf:info
          "WinMx file-sharing application";
        type empty;
      }
      leaf xwindows {
        tailf:info
          "X-Windows remote access";
        type empty;
      }
    }
    leaf-list qos-group {
      tailf:info
        "Qos-group";
      tailf:cli-list-syntax;
      type uint16 {
        tailf:info
          "<0-99>;;Qos Group value";
        range "0..99";
      }
    }
    container source-address {
      tailf:info
        "Source address";
      leaf-list mac {
        tailf:info
          "MAC address";
        tailf:cli-list-syntax;
        type string {
          tailf:info
            "H.H.H;;MAC address";
        }
      }
    }
    leaf-list vlan {
      tailf:info
        "VLANs to match";
      tailf:cli-flat-list-syntax;
      type uint16 {
        tailf:info
          "<1-4094>;;VLAN id";
        range "1..4094";
      }
    }
  }

  grouping ntp-server-grouping {
    list server-list {
      tailf:cli-drop-node-name;
      tailf:cli-suppress-mode;
      tailf:cli-delete-when-empty;
      tailf:cli-compact-syntax;
      tailf:cli-reset-container;
      key "ip-address";
      leaf ip-address {
        tailf:cli-disallow-value "vrf";
        type host-type {
          tailf:info
            "Hostname or A.B.C.D;;IP address of peer";
        }
      }
      leaf key {
        tailf:info
          "Configure peer authentication key";
        type uint32 {
          tailf:info
            "<0-4294967295>;;Peer key number";
        }
      }
      leaf prefer {
        tailf:info
          "Prefer this peer when possible";
        type empty;
      }
      leaf version {
        tailf:info
          "    Configure NTP version";
        type uint8 {
          tailf:info
            "<1-3>;;NTP version number";
        }
      }
    }
  }

  grouping line-grouping {
    container access-class {
      tailf:info
        "Filter connections based on an IP access list";
      tailf:cli-compact-syntax;
      tailf:cli-sequence-commands;
      tailf:cli-reset-container;
      tailf:cli-flatten-container;
      list acccess-list {
        tailf:cli-drop-node-name;
        tailf:cli-compact-syntax;
        tailf:cli-reset-container;
        tailf:cli-suppress-mode;
        tailf:cli-delete-when-empty;
        key "direction";
        leaf direction {
          type enumeration {
            enum "in" {
              tailf:info
                "Filter incoming connections";
            }
            enum "out" {
              tailf:info
                "Filter outgoing connections";
            }
          }
        }
        leaf access-list {
          tailf:cli-drop-node-name;
          tailf:cli-prefix-key;
          type exp-acl-type;
          mandatory true;
        }
        leaf vrf-also {
          tailf:info
            "Same access list is applied for all VRFs";
          type empty;
        }
      }
    }
    leaf escape-character {
      tailf:info
        "Change the current line's escape character";
      type union {
        type uint8 {
          tailf:info
            "ASCII decimal equivalent";
        }
        type enumeration {
          enum "BREAK" {
            tailf:info
              "Cause escape on BREAK";
          }
          enum "DEFAULT" {
            tailf:info
              "Use default escape character";
          }
          enum "NONE" {
            tailf:info
              "Disable escape entirely";
          }
        }
      }
    }
    leaf exec {
      tailf:info
        "Configure EXEC";
      tailf:cli-boolean-no;
      tailf:cli-trim-default;
      type boolean;
      default "true";
    }
    container exec-timeout {
      tailf:info
        "Set the EXEC timeout";
      tailf:cli-sequence-commands;
      tailf:cli-compact-syntax;
      leaf minutes {
        tailf:info
          "<0-35791>;;Timeout in minutes";
        tailf:cli-drop-node-name;
        type uint32;
      }
      leaf seconds {
        tailf:info
          "<0-2147483>;;Timeout in seconds";
        tailf:cli-drop-node-name;
        type uint32;
      }
    }
    container logging {
      tailf:info
        "Modify message logging facilities";
      container synchronous {
        tailf:info
          "Synchronized message output";
        presence "true";
      }
    }
    container login {
      tailf:info
        "Enable password checking";
      tailf:cli-delete-when-empty;
      presence "true";
      leaf local {
        type empty;
      }
      leaf authentication {
        type string;
      }
    }
    container password {
      tailf:info
        "Set a password";
      tailf:cli-compact-syntax;
      tailf:cli-sequence-commands;
      uses password-07-grouping;
    }
    container privilege {
      tailf:info
        "Change privilege level for line";
      leaf level {
        tailf:info
          "Assign default privilege level for line";
        type uint8 {
          tailf:info
            "<0-15>;;Default privilege level for line";
          range "0..15";
        }
      }
    }
    container session-timeout {
      tailf:info
        "Set interval for closing connection when there is no input traffic";
      tailf:cli-sequence-commands;
      tailf:cli-compact-syntax;
      leaf session-timeout-value {
        tailf:cli-drop-node-name;
        type uint16 {
          tailf:info
            "<0-35791>;;Session timeout interval in minutes";
          range "0..35791";
        }
      }
      leaf output {
        tailf:info
          "Include output traffic as well as input traffic";
        type empty;
      }
    }
    leaf stopbits {
      tailf:info
        "Set async line stop bits";
      type enumeration {
        enum "1" {
          tailf:info
            "One stop bit";
        }
        enum "1.5" {
          tailf:info
            "One and one-half stop bits";
        }
        enum "2" {
          tailf:info
            "Two stop bits";
        }
      }
    }
    container telnet {
      tailf:info
        "Telnet protocol-specific configuration";
      leaf transparent {
        tailf:info
          "Send a CR as a CR followed by a NULL instead of a CR followed by a LF";
        type empty;
      }
    }
    container transport {
      tailf:info
        "Define transport protocols for line";
      tailf:cli-incomplete-no;
      leaf-list input {
        tailf:info
          "Define which protocols to use when connecting to the terminal server";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
          enum "lat";
          enum "pad" {
            tailf:info
              "X.3 PAD";
          }
          enum "udptn" {
            tailf:info
              "UDPTN async via UDP protocol";
          }
          enum "rlogin" {
            tailf:info
              "Unix rlogin protocol";
          }
        }
      }
      leaf-list output {
        tailf:info
          "Define which protocols to use for outgoing connections";
        tailf:cli-flat-list-syntax;
        tailf:cli-no-value-on-delete;
        type enumeration {
          enum "all" {
            tailf:info
              "All protocols";
          }
          enum "none" {
            tailf:info
              "No protocols";
          }
          enum "ssh" {
            tailf:info
              "TCP/IP SSH protocol";
          }
          enum "telnet" {
            tailf:info
              "TCP/IP Telnet protocol";
          }
        }
      }
      leaf preferred {
        tailf:info
          "Specify the preferred protocol to use";
        tailf:cli-no-value-on-delete;
        type enumeration {
          enum "none" {
            tailf:info
              "No protocols";
          }
          enum "ssh" {
            tailf:info
              "TCP/IP SSH protocol";
          }
          enum "telnet" {
            tailf:info
              "TCP/IP Telnet protocol";
          }
        }
      }
    }
  }

  grouping queue-size-grouping {
    leaf queue-size-1 {
      tailf:cli-drop-node-name;
      type uint8 {
        tailf:info
          "<1-100>;;enter percent of queue size between 1 and 100";
        range "1..100";
      }
    }
    leaf queue-size-2 {
      tailf:cli-drop-node-name;
      type uint8 {
        tailf:info
          "<1-100>;;enter percent of queue size between 1 and 100";
        range "1..100";
      }
    }
    leaf queue-size-3 {
      tailf:cli-drop-node-name;
      type uint8 {
        tailf:info
          "<1-100>;;enter percent of queue size between 1 and 100";
        range "1..100";
      }
    }
    leaf queue-size-4 {
      tailf:cli-drop-node-name;
      type uint8 {
        tailf:info
          "<1-100>;;enter percent of queue size between 1 and 100";
        range "1..100";
      }
    }
    leaf queue-size-5 {
      tailf:cli-drop-node-name;
      type uint8 {
        tailf:info
          "<1-100>;;enter percent of queue size between 1 and 100";
        range "1..100";
      }
    }
    leaf queue-size-6 {
      tailf:cli-drop-node-name;
      type uint8 {
        tailf:info
          "<1-100>;;enter percent of queue size between 1 and 100";
        range "1..100";
      }
    }
    leaf queue-size-7 {
      tailf:cli-drop-node-name;
      type uint8 {
        tailf:info
          "<1-100>;;enter percent of queue size between 1 and 100";
        range "1..100";
      }
    }
    leaf queue-size-8 {
      tailf:cli-drop-node-name;
      type uint8 {
        tailf:info
          "<1-100>;;enter percent of queue size between 1 and 100";
        range "1..100";
      }
    }
  }

  grouping interface-common-grouping {
    leaf description {
      tailf:info
        "Interface specific description";
      tailf:cli-multi-value;
      tailf:cli-full-command;
      type string {
        length "0..240";
      }
    }
    container authentication {
      tailf:info
        "set the port-control value";
      leaf port-control {
        type enumeration {
          enum "auto" {
            tailf:info
              "PortState will be set to AUTO";
          }
          enum "force-authorized" {
            tailf:info
              "PortState set to Authorized";
          }
          enum "force-unauthorized" {
            tailf:info
              "PortState will be set to UnAuthorized";
          }
        }
      }
    }
    container mab {
      presence "true";
      leaf eap {
        type empty;
      }
    }
    container l2protocol-tunnel {
      tailf:info
        "Tunnel Layer2 protocols";
      tailf:cli-delete-when-empty;
      presence "true";
      leaf cdp {
        tailf:info
          "Cisco Discovery Protocol";
        type empty;
      }
      container drop-threshold {
        tailf:info
          "Set drop threshold for protocol packets";
        leaf packet-rate {
          tailf:cli-drop-node-name;
          type uint16 {
            tailf:info
              "<1-4096>;;Packets/sec rate beyond which protocol packets will be dropped";
            range "1..4096";
          }
        }
        leaf cdp {
          tailf:info
            "Cisco Discovery Protocol";
          type uint16 {
            tailf:info
              "<1-4096>;;Packets/sec rate beyond which protocol packets will be dropped";
            range "1..4096";
          }
        }
        leaf stp {
          tailf:info
            "Spanning Tree Protocol";
          type uint16 {
            tailf:info
              "<1-4096>;;Packets/sec rate beyond which protocol packets will be dropped";
            range "1..4096";
          }
        }
        leaf vtp {
          tailf:info
            "Vlan Trunking Protocol";
          type uint16 {
            tailf:info
              "<1-4096>;;Packets/sec rate beyond which protocol packets will be dropped";
            range "1..4096";
          }
        }
      }
      container shutdown-threshold {
        tailf:info
          "Set shutdown threshold for protocol packets";
        leaf packet-rate {
          tailf:cli-drop-node-name;
          type uint16 {
            tailf:info
              "<1-4096>;;Packets/sec rate beyond which interface is put to err-disable";
            range "1..4096";
          }
        }
        leaf cdp {
          tailf:info
            "Cisco Discovery Protocol";
          type uint16 {
            tailf:info
              "<1-4096>;;Packets/sec rate beyond which interface is put to err-disable";
            range "1..4096";
          }
        }
        leaf stp {
          tailf:info
            "Spanning Tree Protocol";
          type uint16 {
            tailf:info
              "<1-4096>;;Packets/sec rate beyond which interface is put to err-disable";
            range "1..4096";
          }
        }
        leaf vtp {
          tailf:info
            "Vlan Trunking Protocol";
          type uint16 {
            tailf:info
              "<1-4096>;;Packets/sec rate beyond which interface is put to err-disable";
            range "1..4096";
          }
        }
      }
      leaf stp {
        tailf:info
          "Spanning Tree Protocol";
        type empty;
      }
      leaf vtp {
        tailf:info
          "Vlan Trunking Protocol";
        type empty;
      }
    }
    container encapsulation {
      tailf:info
        "Set encapsulation type for an interface";
      container dot1Q {
        tailf:info
          "IEEE 802.1Q Virtual LAN";
        tailf:cli-sequence-commands;
        tailf:cli-compact-syntax;
        leaf vlan-id {
          tailf:cli-drop-node-name;
          type uint16 {
            tailf:info
              "<1-4094>;;IEEE 802.1Q VLAN ID required";
            range "1..4094";
          }
        }
        leaf native {
          tailf:info
            "Make this as native vlan";
          type empty;
        }
      }
      container isl {
        tailf:info
          "Inter Switch Link - Virtual LAN encapsulation";
        tailf:cli-sequence-commands;
        tailf:cli-compact-syntax;
        leaf vlan-id {
          tailf:cli-drop-node-name;
          type uint16 {
            tailf:info
              "<1-4095>;;Virtual LAN Identifier.";
            range "1..4095";
          }
        }
      }
      container ppp {
        tailf:info
          "Point-to-Point protocol";
        presence "true";
      }
      container slip {
        tailf:info
          "Serial Line IP";
        presence "true";
      }
      container frame-relay {
        tailf:info
          "Frame Relay networks";
        tailf:cli-delete-when-empty;
        presence "true";
        leaf ietf {
          tailf:info
            "Use RFC1490/RFC2427 encapsulation";
          type empty;
        }
      }
    }
    container fair-queue-conf {
      tailf:cli-no-keyword;
      tailf:cli-drop-node-name;
      when "not(../name[contains(.,'.')])" {
        tailf:xpath-root 3;
        tailf:dependency "../name";
      }
      leaf fair-queue {
        tailf:cli-boolean-no;
        tailf:cli-trim-default;
        type boolean;
        default "true";
      }
    }
    container fair-queue {
      tailf:info
        "Enable Fair Queuing on an Interface";
      tailf:cli-incomplete-no;
      leaf incomplete {
        type empty;
      }
    }
    container flowcontrol {
      tailf:info
        "Configure flow operation.";
      leaf receive {
        tailf:info
          "Configure receiving flow operation";
        type enumeration {
          enum "desired" {
            tailf:info
              "Allow but do not require flow-control packets on port";
          }
          enum "off" {
            tailf:info
              "Disable flow-control packets on port";
          }
          enum "on" {
            tailf:info
              "Enable flow-control packets on port";
          }
        }
      }
      leaf send {
        tailf:info
          "Configure sending flow operation";
        type enumeration {
          enum "desired" {
            tailf:info
              "Allow but do not require flow-control packets on port";
          }
          enum "off" {
            tailf:info
              "Disable flow-control packets on port";
          }
          enum "on" {
            tailf:info
              "Enable flow-control packets on port";
          }
        }
      }
    }
    choice keepalive-choice {
      leaf keepalive {
        tailf:info
          "Enable keepalive";
        tailf:cli-boolean-no;
        type boolean;
      }
      container keepalive-settings {
        tailf:cli-drop-node-name;
        container keepalive {
          tailf:info
            "Enable keepalive";
          leaf period {
            tailf:cli-drop-node-name;
            type uint16 {
              tailf:info
                "<0-32767>;;Keepalive period (default 10 seconds)";
              range "0..32767";
            }
          }
        }
      }
    }
    container snmp {
      tailf:info
        "Modify SNMP interface parameters";
      container ifindex {
        tailf:info
          "Persist ifindex for the interface";
        choice ifindex-choice {
          leaf persist {
            tailf:info
              "Enable/Disable ifIndex persistence ";
            type empty;
          }
          leaf clear {
            tailf:info
              "Clear Enable/Disable ifIndex persistence";
            tailf:cli-trim-default;
            tailf:cli-boolean-no;
            type boolean;
            default "true";
          }
        }
      }
      container trap {
        tailf:info
          "Allow a specific SNMP trap";
        leaf link-status {
          tailf:info
            "Allow SNMP LINKUP and LINKDOWN traps";
          tailf:cli-boolean-no;
          tailf:cli-trim-default;
          tailf:cli-full-command;
          type boolean;
          default "true";
        }
        container link-status-capas {
          tailf:cli-drop-node-name;
          container link-status {
            tailf:info
              "Allow SNMP LINKUP and LINKDOWN traps";
            container permit {
              tailf:info
                "Permit the following capability";
              leaf duplicates {
                tailf:info
                  "Permit duplicate SNMP LINKUP and LINKDOWN traps";
                type empty;
              }
            }
          }
        }
      }
    }
    container bfd {
      tailf:info
        "BFD interface configuration commands";
      leaf echo {
        tailf:info
          "Use echo adjunct as bfd detection mechanism";
        type empty;
      }
      container interval {
        tailf:info
          "Transmit interval between BFD packets";
        tailf:cli-reset-container;
        tailf:cli-compact-syntax;
        tailf:cli-sequence-commands;
        leaf msecs {
          tailf:cli-drop-node-name;
          tailf:cli-incomplete-command;
          type uint16 {
            tailf:info
              "<100-999>;;Milliseconds";
            range "100..999";
          }
        }
        leaf min_rx {
          tailf:info
            "Minimum receive interval capability";
          tailf:cli-incomplete-command;
          type uint16 {
            tailf:info
              "<100-999>;;Milliseconds";
            range "100..999";
          }
        }
        leaf multiplier {
          tailf:info
            "Multiplier value used to compute holddown";
          type uint8 {
            tailf:info
              "<3-50>;;value used to multiply the interval";
            range "3..50";
          }
        }
      }
    }
    container bandwidth {
      tailf:info
        "Set bandwidth informational parameter";
      tailf:cli-sequence-commands {
        tailf:cli-reset-siblings;
      }
      tailf:cli-compact-syntax;
      leaf inherit {
        tailf:cli-optional-in-sequence;
        tailf:info
          "Specify how bandwidth is inherited";
        type empty;
      }
      leaf kilobits {
        tailf:cli-drop-node-name;
        type uint32 {
          tailf:info
            "<1-10000000>;;Bandwidth in kilobits";
          range "1..10000000";
        }
      }
    }
    container cdp {
      tailf:info
        "CDP interface subcommands";
      leaf enable {
        tailf:info
          "Enable CDP on interface";
        tailf:cli-boolean-no;
        tailf:cli-trim-default;
        tailf:cli-full-command;
        type boolean;
        default "true";
      }
      container tlv {
        tailf:info
          "Enable exchange of specific tlv information";
        container app {
          tailf:info
            "Enable/Configure Application TLV";
          tailf:cli-display-separated;
          tailf:cli-compact-syntax;
          tailf:cli-reset-container;
          tailf:cli-sequence-commands;
          presence "true";
          leaf tlvtype {
            tailf:info
              "Configure APP TLV";
            tailf:cli-incomplete-command;
            type uint16 {
              tailf:info
                "Configure App TLV Type information";
              range "1001..65535";
            }
          }
          leaf value {
            tailf:info
              "Configure App TLV Value information";
            type string {
              tailf:info
                "WORD;;Configure App TLV value information";
            }
          }
        }
        leaf server-location {
          tailf:info
            "Enable CDP location server on interface";
          tailf:cli-full-command;
          type empty;
        }
        leaf location {
          tailf:info
            "Exchange location information";
          tailf:cli-full-command;
          type empty;
        }
      }
    }
    container dampening {
      tailf:info
        "Enable event dampening";
      presence "true";
      leaf dampening-time {
        tailf:cli-drop-node-name;
        tailf:cli-delete-container-on-delete;
        tailf:info
          "<1-30>;;Half-life time for penalty";
        type uint16 {
          range "1..30";
        }
      }
    }
    container hold-queue {
      tailf:info
        "Set hold queue depth";
      tailf:cli-compact-syntax;
      tailf:cli-reset-container;
      tailf:cli-sequence-commands;
      leaf queue-length {
        tailf:cli-drop-node-name;
        type uint16 {
          tailf:info
            "<0-4096>;;Queue length";
          range "0..4096";
        }
      }
      leaf direction {
        tailf:cli-drop-node-name;
        type enumeration {
          enum "in" {
            tailf:info
              "Input queue";
          }
          enum "out" {
            tailf:info
              "Output queue";
          }
        }
      }
    }
    container mpls {
      tailf:info
        "Configure MPLS interface parameters";
      container accounting {
        tailf:info
          "Enable MPLS accounting on this interface";
        container experimental {
          tailf:info
            "Count packets by MPLS experimental value on this interface";
          leaf input {
            tailf:info
              "received packets";
            type empty;
          }
          leaf output {
            tailf:info
              "transmitted packets";
            type empty;
          }
        }
      }
      container bgp {
        tailf:info
          "MPLS BGP";
        leaf forwarding {
          tailf:info
            "Configure MPLS forwarding for directly connected BGP peers";
          type empty;
        }
      }
      leaf ip {
        tailf:info
          "Configure dynamic MPLS forwarding for IP";
        tailf:cli-full-command;
        type empty;
      }
      container label {
        tailf:info
          "Label properties";
        leaf protocol {
          tailf:info
            "Configure label/tag distribution protocol (LDP/TDP)";
          type enumeration {
            enum "both" {
              tailf:info
                "Use LDP or TDP (Adapt to peer on multiaccess interface)";
            }
            enum "ldp" {
              tailf:code-name "lab_ldp";
              tailf:info
                "Use LDP (default)";
            }
            enum "tdp" {
              tailf:code-name "lab_tdp";
              tailf:info
                "Use TDP";
            }
          }
        }
      }
      container ldp {
        tailf:info
          "Configure Label Distribution Protocol (LDP) parameters";
        container discovery {
          tailf:info
            "Configure interface LDP Discovery parameters";
          leaf transport-address {
            tailf:info
              "Specify interface LDP transport address";
            type ldp-discovery-address-type;
          }
        }
      }
      leaf mtu {
        tailf:info
          "Set MPLS Maximum Transmission Unit";
        tailf:cli-full-command;
        type union {
          type uint16 {
            range "1501..1524";
            tailf:info
              "<1501-1524>;;MTU (baby giants bytes)";
          }
          type uint16 {
            range "64..1500";
            tailf:info
              "<64-1500>;;MTU (bytes)";
          }
          type uint16 {
            tailf:info
              "<64-9216>;;MTU size in bytes";
            range "64..9216";
          }
        }
      }
      container traffic-eng {
        tailf:info
          "Configure Traffic Engineering parameters";
        leaf administrative-weight {
          tailf:info
            "Set the administrative weight for the interface";
          tailf:cli-full-command;
          type uint32 {
            range "0..4294967295";
            tailf:info
              "<0-4294967295>;;Weight";
          }
        }
        leaf attribute-flags {
          tailf:info
            "Set user-defined interface attibute flags";
          tailf:cli-full-command;
          type string {
            tailf:info
              "<0x0-0xFFFFFFFF>;;Attribute flags";
          }
        }
        container flooding {
          tailf:info
            "Set flooding parameters";
          container thresholds {
            tailf:info
              "Set flooding thresholds";
            leaf-list down {
              tailf:info
                "Set the thresholds for decreased resource availability";
              tailf:cli-flat-list-syntax;
              type uint8 {
                range "0..100";
                tailf:info
                  "<0-100>;;decreased bandwidth usage (percent)";
              }
            }
            leaf-list up {
              tailf:info
                "Set the thresholds for increased resource availability";
              tailf:cli-flat-list-syntax;
              type uint8 {
                range "0..100";
                tailf:info
                  "<0-100>;;increased bandwidth usage (percent)";
              }
            }
          }
        }
        leaf tunnels {
          tailf:info
            "enable MPLS Traffic Engineering tunnels";
          tailf:cli-full-command;
          type empty;
        }
      }
    }
    choice vrf-choice {
      container ip-vrf {
        tailf:cli-no-keyword;
        tailf:cli-drop-node-name;
        container ip {
          container vrf {
            leaf forwarding {
              tailf:info
                "Configure forwarding table";
              type string {
                tailf:info
                  "WORD;;VRF name";
              }
              tailf:non-strict-leafref {
                path "/ncs:devices/ncs:device/ncs:config/ios:ip/vrf/name" {
                  tailf:xpath-root 3;
                }
              }
            }
          }
        }
      }
      container vrf {
        tailf:info
          "VPN Routing/Forwarding parameters on the interface";
        leaf forwarding {
          tailf:info
            "Configure forwarding table";
          type string {
            tailf:info
              "WORD;;VRF name";
          }
          tailf:non-strict-leafref {
            path "/ncs:devices/ncs:device/ncs:config/ios:vrf/definition/name" {
              tailf:xpath-root 3;
            }
          }
        }
      }
    }
    container ip {
      tailf:info
        "Interface Internet Protocol config commands";
      container access-group {
        tailf:info
          "Specify access control for packets";
        tailf:cli-sequence-commands;
        tailf:cli-compact-syntax;
        leaf access-list {
          tailf:cli-drop-node-name;
          tailf:cli-incomplete-command;
          type exp-acl-type;
        }
        leaf direction {
          tailf:cli-drop-node-name;
          tailf:cli-full-command;
          type enumeration {
            enum "in" {
              tailf:code-name "access_group_direction_in";
              tailf:info
                "inbound packets";
            }
            enum "out" {
              tailf:code-name "access_group_direction_out";
              tailf:info
                "outbound packets";
            }
          }
        }
      }
      container vrf {
        tailf:info
          "VPN Routing/Forwarding parameters on the interface";
        leaf receive {
          tailf:info
            "Add Interface Address into VRF Table";
          tailf:cli-full-command;
          type string {
            tailf:info
              "WORD;;Table name";
          }
        }
        leaf sitemap {
          tailf:info
            "Configure route-map for routesreceived from this site";
          tailf:cli-full-command;
          type string {
            tailf:info
              "WORD;;Name of the route-map";
          }
        }
      }
      choice address-choice {
        leaf unnumbered {
          tailf:info
            "Enable IP processing without an explicit address";
          type string;
        }
        container no-address {
          tailf:cli-drop-node-name;
          leaf address {
            tailf:cli-boolean-no;
            tailf:cli-trim-default;
            type boolean;
            default "true";
          }
        }
        container address {
          tailf:info
            "Set the IP address of an interface";
          tailf:cli-incomplete-command;
          tailf:cli-incomplete-no;
          choice address-choice {
            case fixed-case {
              container primary {
                tailf:cli-drop-node-name;
                tailf:cli-sequence-commands;
                tailf:cli-compact-syntax;
                tailf:cli-incomplete-command;
                tailf:cli-incomplete-no;
                leaf address {
                  tailf:cli-incomplete-command;
                  tailf:cli-drop-node-name;
                  tailf:cli-incomplete-no;
                  tailf:cli-diff-dependency "/ios:vrf/definition/address-family/ipv4" {
                    tailf:xpath-root 3;
                  }
                  tailf:cli-diff-dependency "../../../../vrf/forwarding" {
                    tailf:xpath-root 3;
                  }
                  mandatory true;
                  type inet:ipv4-address {
                    tailf:info
                      "A.B.C.D;;IP address";
                  }
                }
                leaf mask {
                  tailf:cli-drop-node-name;
                  mandatory true;
                  type inet:ipv4-address {
                    tailf:info
                      "A.B.C.D;;IP subnet mask";
                  }
                }
              }
              list secondary {
                key "address";
                tailf:cli-incomplete-command;
                tailf:cli-sequence-commands;
                tailf:cli-compact-syntax;
                tailf:cli-drop-node-name;
                tailf:cli-suppress-mode;
                tailf:cli-incomplete-no;
                leaf address {
                  tailf:cli-incomplete-no;
                  type inet:ipv4-address {
                    tailf:info
                      "A.B.C.D;;IP address";
                  }
                }
                leaf mask {
                  tailf:cli-drop-node-name;
                  tailf:cli-incomplete-command;
                  mandatory true;
                  type inet:ipv4-address {
                    tailf:info
                      "A.B.C.D;;IP subnet mask";
                  }
                }
                leaf secondary {
                  tailf:info
                    "Make this IP address a secondary address";
                  type empty;
                }
              }
            }
            case dhcp-case {
              container dhcp {
                tailf:info
                  "IP Address negotiated via DHCP";
                presence "IP Address negotiated via DHCP";
                tailf:cli-sequence-commands;
                container client-id {
                  tailf:info
                    "Specify client-id to use";
                  tailf:cli-flatten-container;
                  tailf:cli-optional-in-sequence;
                  tailf:cli-diff-dependency "/ios:interface" {
                    tailf:xpath-root 3;
                  }
                  uses ethernet-grouping;
                }
                leaf hostname {
                  tailf:info
                    "Specify value for hostname option";
                  type string {
                    tailf:info
                      "WORD;;hostname string";
                  }
                }
              }
            }
          }
        }
      }
      container flow {
        tailf:info
          "NetFlow related commands";
        leaf ingress {
          tailf:info
            "Enable inbound NetFlow";
          type empty;
        }
        leaf egress {
          tailf:info
            "Enable outbound NetFlow";
          type empty;
        }
      }
      container helper-address {
        tailf:info
          "Specify a destination address for UDP broadcasts";
        tailf:cli-compact-syntax;
        tailf:cli-sequence-commands {
          tailf:cli-reset-siblings;
        }
        choice helper-choice {
          leaf global {
            tailf:info
              "Helper-address is global";
            tailf:cli-optional-in-sequence;
            type empty;
          }
          leaf vrf {
            tailf:info
              "VRF name for helper-address (if different from interface VRF)";
            tailf:cli-optional-in-sequence;
            tailf:cli-diff-dependency "/ios:ip/vrf" {
              tailf:xpath-root 3;
            }
            tailf:cli-diff-dependency "/ios:vrf/definition" {
              tailf:xpath-root 3;
            }
            type string {
              tailf:info
                "WORD;;VPN Routing/Forwarding instance name";
            }
          }
        }
        leaf address {
          tailf:cli-drop-node-name;
          type inet:ipv4-address {
            tailf:info
              "A.B.C.D;;IP destination address";
          }
        }
      }
      container ospf {
        tailf:info
          "OSPF interface commands";
        list process-id {
          tailf:cli-drop-node-name;
          tailf:cli-suppress-mode;
          tailf:cli-delete-when-empty;
          tailf:cli-compact-syntax;
          tailf:cli-incomplete-command;
          tailf:cli-reset-container;
          tailf:cli-sequence-commands;
          key "id";
          leaf id {
            type uint16 {
              tailf:info
                "<1-65535>;;Process ID";
            }
          }
          leaf area {
            type union {
              type uint32 {
                tailf:info
                  "<0-4294967295>;;OSPF area ID as a decimal value";
              }
              type inet:ipv4-address {
                tailf:info
                  "A.B.C.D;;OSPF area ID in IP address format";
              }
            }
          }
          leaf secondaries {
            tailf:info
              "Include or exclude secondary IP addresses";
            type empty;
          }
          leaf none {
            tailf:info
              "Do not include secondary IP addresses";
            type empty;
          }
        }
        leaf network {
          tailf:info
            "Network type";
          type enumeration {
            enum "broadcast" {
              tailf:info
                "Specify OSPF broadcast multi-access network";
            }
            enum "non-broadcast" {
              tailf:info
                "Specify OSPF NBMA network";
            }
            enum "point-to-multipoint" {
              tailf:info
                "Specify OSPF point-to-multipoint network";
            }
            enum "point-to-point" {
              tailf:info
                "Specify OSPF point-to-point network";
            }
          }
        }
        container bfd {
          tailf:info
            "BFD interface configuration commands";
          presence "true";
          leaf enable {
            tailf:cli-full-command;
            tailf:cli-drop-node-name;
            type enumeration {
              enum "disable" {
                tailf:info
                  "Disable BFD for this interface";
              }
            }
          }
        }
        leaf cost {
          tailf:info
            "Interface cost";
          type uint16 {
            tailf:info
              "<1-65535>;;Cost";
            range "1..65535";
          }
        }
      }
      container pim {
        tailf:info
          "PIM interface commands";
        leaf sparse-mode {
          tailf:info
            "Enable PIM sparse-mode operation";
          type empty;
        }
        leaf dr-priority {
          tailf:info
            "PIM router DR priority";
          type uint32 {
            tailf:info
              "<0-4294967294>;;DR priority, preference given to larger value";
          }
        }
      }
      container policy {
        tailf:info
          "Enable policy routing";
        leaf route-map {
          tailf:info
            "Policy route-map";
          type string {
            tailf:info
              "WORD;;Route map name";
          }
        }
      }
      leaf proxy-arp {
        tailf:info
          "Enable proxy ARP";
        tailf:cli-boolean-no;
        tailf:cli-trim-default;
        type boolean;
        default "true";
      }
      container route-cache-conf {
        tailf:cli-no-keyword;
        tailf:cli-drop-node-name;
        leaf route-cache {
          tailf:cli-boolean-no;
          tailf:cli-trim-default;
          type boolean;
          default "true";
        }
      }
      container route-cache {
        tailf:info
          "Enable fast-switching cache for outgoing packets";
        tailf:cli-incomplete-no;
        leaf cef {
          tailf:info
            "Enable Cisco Express Forwarding";
          tailf:cli-boolean-no;
          tailf:cli-trim-default;
          type boolean;
          default "true";
        }
        leaf flow {
          tailf:info
            "Enable Flow fast-switching cache";
          tailf:cli-boolean-no;
          tailf:cli-trim-default;
          type boolean;
          default "false";
        }
        leaf policy {
          tailf:info
            "Enable fast-switching policy cache for outgoing packets";
          tailf:cli-boolean-no;
          tailf:cli-trim-default;
          type boolean;
          default "false";
        }
        leaf same-interface {
          tailf:info
            "Enable fast-switching on the same interface";
          tailf:cli-boolean-no;
          tailf:cli-trim-default;
          type boolean;
          default "false";
        }
      }
      container igmp {
        tailf:info
          "IGMP interface commands";
        container static-group {
          tailf:info
            "IGMP static multicast group";
          list groups {
            tailf:cli-suppress-mode;
            tailf:cli-delete-when-empty;
            tailf:cli-drop-node-name;
            key "name";
            leaf name {
              tailf:cli-suppress-range;
              type union {
                type inet:ipv4-address {
                  tailf:info
                    "A.B.C.D;;IP group address";
                }
                type enumeration {
                  enum "*" {
                    tailf:info
                      "Populated for all groups";
                  }
                }
              }
            }
          }
          list class-map {
            tailf:info
              "Class map of type multicast-flows";
            key "id";
            leaf id {
              type leafref {
                path "/ncs:devices/ncs:device/ncs:config/ios:class-map/name" {
                  tailf:xpath-root 3;
                }
              }
            }
          }
        }
      }
      leaf redirects {
        tailf:info
          "Enable sending ICMP Redirect messages";
        type empty;
      }
      container tcp {
        tailf:info
          "TCP header compression and other parameters";
        leaf adjust-mss {
          tailf:info
            "Adjust the mss of transit packets";
          type uint16 {
            tailf:info
              "<500-1460>;;Maximum segment size in bytes";
            range "500..1460";
          }
        }
      }
      container virtual-reassembly {
        tailf:cli-compact-syntax;
        leaf max-reassemblies {
          type uint32;
        }
        leaf max-fragments {
          type uint32;
        }
        leaf timeout {
          type uint32;
        }
        leaf drop-fragments {
          type empty;
        }
        leaf in {
          type empty;
        }
      }
      container dhcp {
        tailf:info
          "Configure DHCP parameters for this interface";
        container relay {
          tailf:info
            "DHCP relay configuration parameters";
          container information {
            tailf:info
              "DHCP relay information option";
            container check-reply {
              tailf:info
                "Validate relay information in BOOTREPLY";
              presence "true";
              leaf none {
                tailf:info
                  "Set to none";
                type empty;
              }
            }
            container option {
              tailf:info
                "DHCP relay information option";
              leaf subscriber-id {
                tailf:info
                  "Subscriber identifier sub option";
                type string {
                  tailf:info
                    "WORD;;Subscriber identifier string";
                }
              }
            }
            container option-insert {
              tailf:info
                "Insert relay information in BOOTREQUEST";
              presence "true";
              leaf none {
                tailf:info
                  "Set to none";
                type empty;
              }
            }
            leaf policy-action {
              tailf:info
                "Define reforwarding policy";
              type enumeration {
                enum "drop" {
                  tailf:info
                    "Do not forward BOOTREQUEST message";
                }
                enum "encapsulate" {
                  tailf:info
                    "Encapsulate existing information";
                }
                enum "keep" {
                  tailf:info
                    "Leave existing information alone";
                }
                enum "replace" {
                  tailf:info
                    "Replace existing information";
                }
              }
            }
            leaf trusted {
              tailf:info
                "Received DHCP packet may contain relay info option with zero giaddr";
              type empty;
            }
          }
        }
        container snooping {
          tailf:info
            "DHCP Snooping";
          container limit {
            tailf:info
              "DHCP Snooping limit";
            leaf rate {
              tailf:info
                "DHCP Snooping limit";
              type uint16 {
                tailf:info
                  "<1-2048>;;DHCP snooping rate limit";
                range "1..2048";
              }
            }
          }
          leaf trust {
            tailf:info
              "DHCP Snooping trust config";
            type empty;
          }
          list vlan {
            tailf:info
              "DHCP Snooping vlan";
            key "id";
            max-elements 1;
            leaf id {
              tailf:cli-drop-node-name;
              type uint16 {
                tailf:info
                  "<1-4094>;;DHCP Snooping vlan";
                range "1..4094";
              }
            }
            container information {
              tailf:info
                "DHCP Snooping information";
              container option {
                tailf:info
                  "DHCP Snooping information option";
                container format-type {
                  tailf:info
                    "Option 82 information format";
                  container circuit-id {
                    tailf:info
                      "Circuit id option 82 format";
                    leaf string {
                      tailf:info
                        "User defined string for circuit id";
                      type string {
                        tailf:info
                          "WORD;;Use string for circuit id (3-63 chars)";
                        length "3..63";
                      }
                    }
                  }
                }
              }
            }
          }
        }
      }
      leaf mtu {
        tailf:info
          "Set IP Maximum Transmission Unit";
        type uint16 {
          tailf:info
            "<68-9198>;;MTU (bytes)";
          range "68..9198";
        }
      }
      container nat {
        tailf:info
          "NAT interface commands";
        leaf allow-static-host {
          tailf:info
            "Allow static-ip clients";
          type empty;
        }
        leaf enable {
          tailf:info
            "Enable Address Translation (NVI)";
          type empty;
        }
        choice nat-choice {
          leaf inside {
            tailf:info
              "Inside interface for address translation";
            type empty;
          }
          leaf outside {
            tailf:info
              "Outside interface for address translation";
            type empty;
          }
        }
      }
    }
    container ipv6 {
      tailf:info
        "IPv6 interface subcommands";
      container address {
        tailf:info
          "Configure IPv6 address on interface";
        choice address-choice {
          case autoconfig-case {
            container autoconfig {
              tailf:info
                "Obtain address using autoconfiguration";
              presence "true";
              leaf default {
                tailf:info
                  "Insert default route";
                type empty;
              }
            }
          }
          case manual-case {
            list prefix-list {
              tailf:cli-drop-node-name;
              tailf:cli-suppress-mode;
              tailf:cli-delete-when-empty;
              key "prefix";
              leaf prefix {
                type ios:ipv6-prefix {
                  tailf:info
                    "X:X:X:X::X/<0-128>;;IPv6 prefix";
                }
              }
              leaf anycast {
                tailf:info
                  "Configure as an anycast";
                tailf:cli-full-command;
                type empty;
              }
              leaf eui-64 {
                tailf:info
                  "Use eui-64 interface identifier";
                tailf:cli-full-command;
                type empty;
              }
            }
          }
        }
      }
      leaf enable {
        tailf:info
          "Enable IPv6 on interface";
        type empty;
      }
      container ospf {
        tailf:info
          "OSPF interface commands";
        list process {
          tailf:cli-suppress-mode;
          tailf:cli-delete-when-empty;
          tailf:cli-drop-node-name;
          tailf:cli-compact-syntax;
          tailf:cli-sequence-commands {
            tailf:cli-reset-siblings;
          }
          key "id";
          leaf id {
            type uint16 {
              tailf:info
                "<1-65535>;;Process ID";
              range "1..65535";
            }
          }
          leaf area {
            tailf:info
              "Set the OSPF area ID";
            type union {
              type uint32 {
                tailf:info
                  "<0-4294967295>;;OSPF area ID as a decimal value";
                range "0..4294967295";
              }
              type inet:ipv4-address {
                tailf:info
                  "A.B.C.D;;OSPF area ID in IP address format";
              }
            }
          }
          leaf instance {
            tailf:info
              "Set the OSPF instance";
            type union {
              type uint8 {
                tailf:info
                  "<0-31>;;Instance ID";
                range "0..31";
              }
              type uint8 {
                tailf:info
                  "<32-255>;;Instance ID (DEPRECATED!)";
                range "32..255";
              }
            }
          }
        }
        container bfd {
          tailf:info
            "Enable BFD on this interface";
          presence "true";
          leaf disable {
            tailf:info
              "Disable BFD on this interface";
            type empty;
          }
        }
        leaf cost {
          tailf:info
            "Route cost of this interface";
          type uint16 {
            tailf:info
              "<1-65535>;;Route cost of this interface";
            range "1..65535";
          }
        }
        container database-filter {
          tailf:info
            "Filter OSPF LSA during synchronization and flooding";
          choice database {
            leaf all {
              tailf:info
                "Filter all LSA";
              type enumeration {
                enum "out" {
                  tailf:info
                    "Outgoing LSA";
                }
              }
            }
            leaf disable {
              tailf:info
                "Disable LSA Filter on this interface";
              type empty;
            }
          }
        }
        leaf dead-interval {
          tailf:info
            "Interval after which a neighbor is declared dead";
          type uint16 {
            tailf:info
              "<1-65535>;;Seconds";
            range "1..65535";
          }
        }
        container demand-circuit {
          tailf:info
            "OSPF demand circuit";
          presence "true";
          leaf disable {
            tailf:info
              "Disable demand circuit on this interface";
            type empty;
          }
        }
        container flood-reduction {
          tailf:info
            "OSPF Flood Reduction";
          presence "true";
          leaf disable {
            tailf:info
              "Disable Flood Reduction on this interface";
            type empty;
          }
        }
        leaf hello-interval {
          tailf:info
            "Time between HELLO packets";
          type uint16 {
            tailf:info
              "<1-65535>;;Seconds";
            range "1..65535";
          }
        }
        container mtu-ignore {
          tailf:info
            "Ignores the MTU in DBD packets";
          presence "true";
          leaf disable {
            tailf:info
              "Disable Ingore MTU on this interface";
            type empty;
          }
        }
        leaf priority {
          tailf:info
            "Router priority";
          type uint16 {
            tailf:info
              "<0-255>;;Priority";
            range "0..255";
          }
        }
        leaf retransmit-interval {
          tailf:info
            "Time between retransmitting lost link state advertisements";
          type uint16 {
            tailf:info
              "<1-65535>;;Seconds";
            range "1..65535";
          }
        }
        leaf transmit-delay {
          tailf:info
            "Link state transmit delay";
          type uint16 {
            tailf:info
              "<1-65535>;;Seconds";
            range "1..65535";
          }
        }
      }
      leaf mtu {
        tailf:info
          "Set IPv6 Maximum Transmission Unit";
        type uint16 {
          tailf:info
            "<1280-9198>;;MTU (bytes)";
          range "1280..9198";
        }
      }
    }
    leaf load-interval {
      tailf:info
        "Specify interval for load calculation for an interface";
      type uint16 {
        tailf:info
          "<30-600>;;Load interval delay in seconds";
        range "0..600";
      }
    }
    leaf max-reserved-bandwidth {
      tailf:info
        "Maximum Reservable Bandwidth on an Interface";
      tailf:cli-full-command;
      type uint8 {
        tailf:info
          "<1-100>;;Max. reservable bandwidth as percent of interface bandwidth";
        range "1..100";
      }
    }
    container mls {
      tailf:info
        "mls sub/interface commands";
      container qos {
        tailf:info
          "qos command keyword";
        leaf channel-consistency {
          tailf:info
            "enable or disable qos consistency checks";
          tailf:cli-full-command;
          tailf:cli-boolean-no;
          tailf:cli-trim-default;
          type boolean;
          default "true";
        }
        leaf trust {
          tailf:info
            "trust keyword";
          tailf:cli-full-command;
          type enumeration {
            enum "cos" {
              tailf:info
                "cos keyword";
            }
            enum "dscp" {
              tailf:info
                "dscp keyword";
            }
            enum "ip-precedence" {
              tailf:info
                "ip-precedence keyword";
            }
          }
        }
        leaf vlan-based {
          tailf:info
            "vlan-based keyword";
          tailf:cli-full-command;
          type empty;
        }
      }
    }
    leaf mtu {
      tailf:info
        "Set the interface Maximum Transmission Unit (MTU)";
      tailf:cli-full-command;
      type uint16 {
        range "64..18000";
        tailf:info
          "<64-18000>;;MTU size in bytes";
      }
    }
    container power {
      container inline {
        leaf consumption {
          tailf:cli-full-command;
          type uint16 {
            range "4000..15400";
          }
        }
      }
    }
    container service-policy {
      tailf:info
        "Configure QoS Service Policy";
      leaf history {
        tailf:cli-full-command;
        tailf:info
          "Keep history of QoS metrics";
        type empty;
      }
      leaf input {
        tailf:cli-full-command;
        tailf:info
          "Assign policy-map to the input of an interface";
        type string {
          tailf:info
            "WORD;;policy-map name";
        }
        tailf:non-strict-leafref {
          path "/ncs:devices/ncs:device/ncs:config/ios:policy-map/ios:name" {
            tailf:xpath-root 3;
          }
        }
      }
      leaf output {
        tailf:cli-full-command;
        tailf:info
          "Assign policy-map to the output of an interface";
        type string {
          tailf:info
            "WORD;;policy-map name";
        }
        tailf:non-strict-leafref {
          path "/ncs:devices/ncs:device/ncs:config/ios:policy-map/ios:name" {
            tailf:xpath-root 3;
          }
        }
      }
      container type {
        tailf:info
          "Configure CPL Service Policy";
        container performance-monitor {
          tailf:info
            "Configure media monitor service-policy type";
          tailf:cli-sequence-commands;
          tailf:cli-compact-syntax;
          leaf direction {
            tailf:cli-drop-node-name;
            type enumeration {
              enum "input" {
                tailf:info
                  "Assign policy-map to the input of an interfcae";
              }
              enum "output" {
                tailf:info
                  "Assign policy-map to the output of an interfcae";
              }
            }
          }
          leaf name {
            tailf:cli-drop-node-name;
            type string {
              tailf:info
                "WORD;;policy-map name";
            }
            tailf:non-strict-leafref {
              path "/ncs:devices/ncs:device/ncs:config/ios:policy-map/name" {
                tailf:xpath-root 3;
              }
            }
          }
        }
      }
    }
    leaf shutdown {
      tailf:info
        "Shutdown the selected interface";
      tailf:cli-full-command;
      type empty;
    }
    container standby {
      tailf:info
        "HSRP interface configuration commands";
      leaf version {
        tailf:info
          "HSRP version";
        tailf:cli-full-command;
        type enumeration {
          tailf:info
            "<1-2>;;Version number";
          enum "1";
          enum "2";
        }
      }
      leaf bfd {
        tailf:info
          "Enable HSRP BFD";
        type empty;
      }
      container delay {
        tailf:info
          "HSRP initialisation delay";
        tailf:cli-compact-syntax;
        leaf minimum {
          tailf:info
            "Minimum delay";
          type uint16 {
            tailf:info
              "<0-10000>;;Delay in seconds";
            range "0..10000";
          }
        }
        leaf reload {
          tailf:info
            "Delay after reload";
          type uint16 {
            tailf:info
              "<0-10000>;;Delay in seconds";
            range "0..10000";
          }
        }
      }
      leaf mac-refresh {
        tailf:info
          "Refresh MAC cache on switch by periodically sending packet from virtual mac address";
        type uint8 {
          tailf:info
            "<0-255>;;Interval to refresh MAC cache";
          range "0..255";
        }
      }
      container use-bia {
        tailf:info
          "HSRP uses interface's burned in address";
        presence "true";
        container scope {
          tailf:info
            "Specify the scope of use-bia";
          leaf interface {
            tailf:info
              "Use-bia applies to all groups on this interface or sub-interface";
            type empty;
          }
        }
      }
      list standby-list {
        tailf:cli-drop-node-name;
        tailf:cli-suppress-mode;
        tailf:cli-delete-when-empty;
        tailf:cli-incomplete-command;
        key "group-number";
        leaf group-number {
          tailf:cli-suppress-range;
          type uint16 {
            tailf:info
              "<0-255>;;group number";
          }
        }
        container authentication {
          tailf:info
            "Authentication";
          choice auth {
            leaf word {
              tailf:cli-drop-node-name;
              tailf:cli-disallow-value "md5|text";
              type string {
                tailf:info
                  "WORD;;Plain text authentication string (8 chars max)";
              }
            }
            container md5 {
              tailf:info
                "Use MD5 authentication";
              leaf key-chain {
                tailf:info
                  "Set key chain";
                type string {
                  tailf:info
                    "WORD;;Name of key-chain";
                }
              }
              container key-string {
                tailf:info
                  "Set key string";
                tailf:cli-compact-syntax;
                tailf:cli-sequence-commands {
                  tailf:cli-reset-siblings;
                }
                leaf encrypt {
                  tailf:cli-drop-node-name;
                  type enumeration {
                    enum "0" {
                      tailf:info
                        "Specifies an UNENCRYPTED key string will follow";
                    }
                    enum "7" {
                      tailf:info
                        "Specifies a HIDDEN key string will follow";
                    }
                  }
                }
                leaf string {
                  tailf:cli-drop-node-name;
                  type string {
                    tailf:info
                      "WORD;;Key string (64 chars max)";
                  }
                }
                leaf timeout {
                  tailf:info
                    "Set timeout";
                  type uint16 {
                    tailf:info
                      "<0-32767>;;Timeout until only accepting new key (seconds)";
                    range "0..32767";
                  }
                }
              }
            }
            leaf text {
              tailf:info
                "Plain text authentication";
              type string {
                tailf:info
                  "WORD;;Plain text authentication string (8 chars max)";
              }
            }
          }
        }
        leaf follow {
          tailf:info
            "Name of HSRP group to follow";
          type string {
            tailf:info
              "WORD;;name string (25 chars. max)";
          }
        }
        container ip {
          tailf:info
            "Enable HSRP and set the virtual IP address";
          tailf:cli-sequence-commands;
          tailf:cli-compact-syntax;
          presence "true";
          leaf address {
            tailf:cli-drop-node-name;
            type inet:ipv4-address {
              tailf:info
                "A.B.C.D;;Virtual IP address";
            }
          }
          leaf secondary {
            tailf:info
              "Make this IP address a secondary virtual IP address";
            type empty;
          }
        }
        leaf ipv6 {
          tailf:info
            "Enable HSRP IPv6";
          type union {
            type inet:ipv6-address {
              tailf:info
                "X:X:X:X::X;;IPv6 link-local address";
            }
            type ios:ipv6-prefix;
            type enumeration {
              enum "autoconfig" {
                tailf:info
                  "Obtain address using autoconfiguration";
              }
            }
          }
        }
        leaf mac-address {
          tailf:info
            "Virtual MAC address";
          type string {
            tailf:info
              "H.H.H;;MAC address";
          }
        }
        leaf name {
          tailf:info
            "Redundancy name string";
          tailf:cli-full-command;
          type string {
            tailf:info
              "WORD;;name string";
          }
        }
        container preempt {
          tailf:info
            "Overthrow lower priority Active routers";
          presence "true";
          container delay {
            tailf:info
              "Wait before preempting";
            tailf:cli-compact-syntax;
            leaf minimum {
              tailf:info
                "Delay at least this long";
              type uint16 {
                tailf:info
                  "<0-3600>;;Number of seconds for minimum delay";
                range "0..3600";
              }
            }
            leaf reload {
              tailf:info
                "Delay after reload";
              type uint16 {
                tailf:info
                  "<0-3600>;;Number of seconds for reload delay";
                range "0..3600";
              }
            }
            leaf sync {
              tailf:info
                "Wait for IP redundancy client";
              type uint16 {
                tailf:info
                  "<0-3600>;;Number of seconds for sync delay";
                range "0..3600";
              }
            }
          }
        }
        leaf priority {
          tailf:info
            "Priority level";
          tailf:cli-full-command;
          type uint8 {
            tailf:info
              "<0-255>;;Priority value";
          }
        }
        container redirect {
          tailf:info
            "Configure sending of ICMP Redirect messages with an HSRP virtual IP address as the gateway IP address";
          container advertisement {
            tailf:info
              "Redirect advertisement messages";
            container authentication {
              tailf:info
                "Authentication";
              container md5 {
                tailf:info
                  "Use MD5 authentication";
                leaf key-chain {
                  tailf:info
                    "Set key chain";
                  type string {
                    tailf:info
                      "WORD;;Name of key-chain";
                  }
                }
                container key-string {
                  tailf:info
                    "Set key string";
                  tailf:cli-compact-syntax;
                  tailf:cli-sequence-commands {
                    tailf:cli-reset-siblings;
                  }
                  leaf encrypt {
                    tailf:cli-drop-node-name;
                    type enumeration {
                      enum "0" {
                        tailf:info
                          "Specifies an UNENCRYPTED key string will follow";
                      }
                      enum "7" {
                        tailf:info
                          "Specifies a HIDDEN key string will follow";
                      }
                    }
                  }
                  leaf string {
                    tailf:cli-drop-node-name;
                    type string {
                      tailf:info
                        "WORD;;Key string (64 chars max)";
                    }
                  }
                  leaf timeout {
                    tailf:info
                      "Set timeout";
                    type uint16 {
                      tailf:info
                        "<0-32767>;;Timeout until only accepting new key (seconds)";
                      range "0..32767";
                    }
                  }
                }
              }
            }
          }
          container timers {
            tailf:info
              "Adjust redirect timers";
            tailf:cli-compact-syntax;
            tailf:cli-sequence-commands {
              tailf:cli-reset-siblings;
            }
            leaf advertisement {
              tailf:cli-drop-node-name;
              type uint16 {
                tailf:info
                  "<10-180>;;Passive router advertisement interval in seconds";
                range "10..180";
              }
            }
            leaf holddown {
              tailf:cli-drop-node-name;
              type uint16 {
                tailf:info
                  "<30-3600>;;Passive router holddown interval in seconds";
                range "30..3600";
              }
            }
          }
          leaf unknown {
            tailf:info
              "Redirect to non-HSRP routers";
            type empty;
          }
        }
        container timers {
          tailf:info
            "Hello and hold timers";
          tailf:cli-compact-syntax;
          tailf:cli-sequence-commands {
            tailf:cli-reset-siblings;
          }
          container hello-interval {
            tailf:cli-drop-node-name;
            tailf:cli-flatten-container;
            tailf:cli-compact-syntax;
            choice hello-interval-choice {
              leaf seconds {
                tailf:cli-drop-node-name;
                tailf:cli-incomplete-command;
                type uint8 {
                  tailf:info
                    "<1-254>;;Hello interval in seconds";
                  range "1..254";
                }
              }
              leaf msec {
                tailf:info
                  "Specify hello interval in milliseconds";
                tailf:cli-incomplete-command;
                type uint16 {
                  tailf:info
                    "<15-999>;;Hello interval in milliseconds";
                  range "15..999";
                }
              }
            }
          }
          container hold-time {
            tailf:cli-drop-node-name;
            tailf:cli-flatten-container;
            tailf:cli-compact-syntax;
            choice hold-time-choice {
              leaf seconds {
                tailf:cli-drop-node-name;
                type uint8 {
                  tailf:info
                    "<1-255>;;Hold time in seconds";
                  range "1..255";
                }
              }
              leaf msec {
                tailf:info
                  "Specify hold time in milliseconds";
                type uint16 {
                  tailf:info
                    "<50-3000>;;Hello interval in milliseconds";
                  range "50..3000";
                }
              }
            }
          }
        }
      }
    }
    container storm-control {
      tailf:info
        "storm configuration";
      container action {
        tailf:info
          "Action to take for storm..control;";
        leaf level {
          tailf:info
            "Set storm suppression level on this interface";
          type decimal64 {
            fraction-digits 2;
            tailf:info
              "<0-100>;;Enter Integer part of level as percentage of bandwidth";
            range "0..100";
          }
        }
      }
      container broadcast {
        tailf:info
          "Broadcast address storm control";
        leaf level {
          tailf:info
            "Set storm suppression level on this interface";
          type decimal64 {
            fraction-digits 2;
            tailf:info
              "<0-100>;;Enter Integer part of level as percentage of bandwidth";
            range "0..100";
          }
        }
      }
      container multicast {
        tailf:info
          "Multicast address storm control";
        leaf level {
          tailf:info
            "Set storm suppression level on this interface";
          type decimal64 {
            fraction-digits 2;
            tailf:info
              "<0-100>;;Enter Integer part of level as percentage of bandwidth";
            range "0..100";
          }
        }
      }
      container unicast {
        tailf:info
          "Unicast address storm control";
        leaf level {
          tailf:info
            "Set storm suppression level on this interface";
          type decimal64 {
            fraction-digits 2;
            tailf:info
              "<0-100>;;Enter Integer part of level as percentage of bandwidth";
            range "0..100";
          }
        }
      }
    }
    container wrr-queue {
      tailf:info
        "Configure weighted round-robin xmt queues";
      container bandwidth {
        tailf:info
          "Configure WRR minimum bandwidth with weights or percentages";
        tailf:cli-compact-syntax;
        tailf:cli-sequence-commands {
          tailf:cli-reset-siblings;
        }
        choice bandwidth-choice {
          case a {
            leaf weight-1 {
              tailf:cli-drop-node-name;
              type uint8 {
                tailf:info
                  "<0-255>;;enter bandwidth weight";
                range "0..255";
              }
            }
            leaf weight-2 {
              tailf:cli-drop-node-name;
              type uint8 {
                tailf:info
                  "<0-255>;;enter bandwidth weight";
                range "0..255";
              }
            }
            leaf weight-3 {
              tailf:cli-drop-node-name;
              type uint8 {
                tailf:info
                  "<0-255>;;enter bandwidth weight";
                range "0..255";
              }
            }
            leaf weight-4 {
              tailf:cli-drop-node-name;
              type uint8 {
                tailf:info
                  "<0-255>;;enter bandwidth weight";
                range "0..255";
              }
            }
            leaf weight-5 {
              tailf:cli-drop-node-name;
              type uint8 {
                tailf:info
                  "<0-255>;;enter bandwidth weight";
                range "0..255";
              }
            }
            leaf weight-6 {
              tailf:cli-drop-node-name;
              type uint8 {
                tailf:info
                  "<0-255>;;enter bandwidth weight";
                range "0..255";
              }
            }
            leaf weight-7 {
              tailf:cli-drop-node-name;
              type uint8 {
                tailf:info
                  "<0-255>;;enter bandwidth weight";
                range "0..255";
              }
            }
          }
          case b {
            container percent {
              tailf:cli-compact-syntax;
              tailf:cli-sequence-commands {
                tailf:cli-reset-siblings;
              }
              leaf percent-1 {
                tailf:cli-drop-node-name;
                type uint8 {
                  tailf:info
                    "<0-100>;;enter bandwidth percent";
                  range "0..100";
                }
              }
              leaf percent-2 {
                tailf:cli-drop-node-name;
                type uint8 {
                  tailf:info
                    "<0-100>;;enter bandwidth percent";
                  range "0..100";
                }
              }
              leaf percent-3 {
                tailf:cli-drop-node-name;
                type uint8 {
                  tailf:info
                    "<0-100>;;enter bandwidth percent";
                  range "0..100";
                }
              }
              leaf percent-4 {
                tailf:cli-drop-node-name;
                type uint8 {
                  tailf:info
                    "<0-100>;;enter bandwidth percent";
                  range "0..100";
                }
              }
              leaf percent-5 {
                tailf:cli-drop-node-name;
                type uint8 {
                  tailf:info
                    "<0-100>;;enter bandwidth percent";
                  range "0..100";
                }
              }
              leaf percent-6 {
                tailf:cli-drop-node-name;
                type uint8 {
                  tailf:info
                    "<0-100>;;enter bandwidth percent";
                  range "0..100";
                }
              }
              leaf percent-7 {
                tailf:cli-drop-node-name;
                type uint8 {
                  tailf:info
                    "<0-100>;;enter bandwidth percent";
                  range "0..100";
                }
              }
            }
          }
        }
      }
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
      container queue-limit {
        tailf:info
          "Configure queue-limit";
        tailf:cli-compact-syntax;
        tailf:cli-sequence-commands {
          tailf:cli-reset-siblings;
        }
        leaf weight-a {
          tailf:cli-drop-node-name;
          type uint8 {
            tailf:info
              "<0-100>;;enter queue size weight";
            range "0..100";
          }
        }
        leaf weight-b {
          tailf:cli-drop-node-name;
          type uint8 {
            tailf:info
              "<0-100>;;enter queue size weight";
            range "0..100";
          }
        }
        leaf weight-c {
          tailf:cli-drop-node-name;
          type uint8 {
            tailf:info
              "<0-100>;;enter queue size weight";
            range "0..100";
          }
        }
      }
      container random-detect {
        tailf:info
          "Configure random-detect";
        list max-threshold {
          tailf:info
            "Max threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses queue-size-grouping;
        }
        list min-threshold {
          tailf:info
            "Min threshold for WRED";
          tailf:cli-suppress-mode;
          tailf:cli-delete-when-empty;
          tailf:cli-compact-syntax;
          tailf:cli-sequence-commands {
            tailf:cli-reset-siblings;
          }
          key "id";
          leaf id {
            type uint8 {
              tailf:info
                "<1-3>;;enter queue id";
              range "1..3";
            }
          }
          uses queue-size-grouping;
        }
      }
      list threshold {
        tailf:info
          "Configure queue tail-drop thresholds";
        tailf:cli-suppress-mode;
        tailf:cli-delete-when-empty;
        tailf:cli-compact-syntax;
        tailf:cli-sequence-commands {
          tailf:cli-reset-siblings;
        }
        key "id";
        leaf id {
          type uint8 {
            tailf:info
              "<1-3>;;enter queue id";
            range "1..3";
          }
        }
        uses queue-size-grouping;
      }
    }
    container priority-queue {
      tailf:info
        "Configure priority scheduling";
      container cos-map {
        tailf:info
          "Configure cos-map for a queue";
        tailf:cli-compact-syntax;
        tailf:cli-sequence-commands {
          tailf:cli-reset-siblings;
        }
        leaf id {
          tailf:cli-drop-node-name;
          type uint8;
        }
        leaf-list cos-values {
          tailf:cli-drop-node-name;
          tailf:cli-flat-list-syntax;
          max-elements 8;
          type uint8 {
            tailf:info
              "<0-7>;;cos values separated by spaces (up to 8 values total)";
            range "0..7";
          }
        }
      }
      leaf out {
        tailf:info
          "egress priority queue";
        tailf:cli-full-command;
        type empty;
      }
    }
    container rep {
      tailf:info
        "Resilient Ethernet Protocol characteristics";
      container block {
        tailf:info
          "Block port & VLANs for VLAN Load-balancing";
        container port {
          tailf:info
            "Specify port for VLAN Load-balancing";
          tailf:cli-sequence-commands {
            tailf:cli-reset-siblings;
          }
          tailf:cli-compact-syntax;
          choice port-choice {
            leaf neighbor-offset {
              tailf:cli-drop-node-name;
              type int16 {
                tailf:info
                  "<-256 - 256>;;Neighbor offset";
                range "-256..256";
              }
            }
            leaf id {
              tailf:info
                "REP port ID";
              type string {
                tailf:info
                  "WORD;;REP port ID (16 digit hexadecimal number)";
              }
            }
            leaf preferred {
              tailf:info
                "Preferred flag";
              type empty;
            }
          }
          leaf vlan {
            tailf:info
              "VLANs to block";
            type union {
              type string {
                tailf:info
                  "WORD;;VLAN list (1-4094) ex: 1-65,72,300-320";
              }
              type enumeration {
                enum "all" {
                  tailf:info
                    "All VLANs";
                }
              }
            }
          }
        }
      }
      container preempt {
        tailf:info
          "Preemption options";
        leaf delay {
          tailf:info
            "Delay timer in seconds";
          type uint16 {
            tailf:info
              "<15-300>;;number of seconds before automatic preemption takes place";
            range "15..300";
          }
        }
      }
      container segment {
        tailf:info
          "REP segment ID";
        tailf:cli-compact-syntax;
        tailf:cli-sequence-commands {
          tailf:cli-reset-siblings;
        }
        leaf id {
          tailf:cli-drop-node-name;
          type uint16 {
            tailf:info
              "<1-1024>;;Between 1 and 1024";
            range "1..1024";
          }
        }
        leaf edge {
          tailf:info
            "Edge Port";
          tailf:cli-optional-in-sequence;
          type empty;
        }
        leaf primary {
          tailf:info
            "Primary Edge Port";
          tailf:cli-optional-in-sequence;
          when '../edge' {
            tailf:xpath-root 3;
            tailf:dependency "../edge";
          }
          type empty;
        }
        leaf preferred {
          tailf:info
            "Preferred Alternate Port";
          type empty;
        }
      }
      container stcn {
        tailf:info
          "Segment Topology Change Notification";
        leaf segment {
          tailf:info
            "for REP segment";
          type string {
            tailf:info
              "WORD;;segment ID list (1-1024) ex: 1-3,6-9";
          }
        }
        leaf stp {
          tailf:info
            "for STP network";
          type empty;
        }
      }
    }
    container rcv-queue {
      tailf:info
        "Configure receive queue(s)";
      list cos-map {
        tailf:info
          "Configure cos-map for a queue threshold";
        tailf:cli-suppress-mode;
        tailf:cli-delete-when-empty;
        tailf:cli-compact-syntax;
        tailf:cli-sequence-commands {
          tailf:cli-reset-siblings;
        }
        key "queue-id threshold-id";
        leaf queue-id {
          type uint8 {
            tailf:info
              "<1-3>;;enter cos-map queue id";
            range "1..3";
          }
        }
        leaf threshold-id {
          type uint8 {
            tailf:info
              "<1-8>;;enter cos-map threshhold id";
            range "1..8";
          }
        }
        leaf-list cos-values {
          tailf:cli-drop-node-name;
          tailf:cli-flat-list-syntax;
          max-elements 8;
          type uint8 {
            tailf:info
              "<0-7>;;cos values separated by spaces (up to 8 values total)";
            range "0..7";
          }
        }
      }
    }
    container udld {
      tailf:info
        "Configure UDLD enabled or disabled and ignore global UDLD setting";
      container port {
        tailf:info
          "Enable UDLD protocol on this interface despite global UDLD setting";
        tailf:cli-delete-when-empty;
        presence "true";
        choice port-choice {
          leaf aggressive {
            tailf:info
              "Enable UDLD protocol in aggressive mode on this interface despite global UDLD setting";
            type empty;
          }
          leaf disable {
            tailf:info
              "Disable UDLD protocol on this interface despite global UDLD setting";
            type empty;
          }
        }
      }
    }
    container peer {
      tailf:info
        "Peer parameters for point to point interfaces";
      container default {
        tailf:info
          "Specify default parameters";
        container ip {
          tailf:info
            "Specify default IP parameters";
          container address {
            tailf:info
              "Specify default IP address";
            choice address-choice {
              leaf dhcp {
                tailf:info
                  "Use DHCP proxy client mechanism to allocate a peer IP address";
                type empty;
              }
              container dhcp-pool {
                tailf:info
                  "Use local DHCP pools to allocate a peer IP address";
                presence "true";
                leaf pools {
                  tailf:cli-drop-node-name;
                  tailf:cli-multi-value;
                  type string {
                    tailf:info
                      "LINE;;List of one or more DHCP address pools";
                  }
                }
              }
              container pool {
                tailf:info
                  "Use IP pool mechanism to allocate a peer IP address";
                presence "true";
                leaf pools {
                  tailf:cli-drop-node-name;
                  tailf:cli-multi-value;
                  type string {
                    tailf:info
                      "LINE;;List of one or more DHCP address pools";
                  }
                }
              }
            }
          }
        }
      }
    }
  }

  grouping interface-ethernet-grouping {
    container carrier-delay {
      tailf:info
        "Specify delay for interface transitions";
      choice delay-choice {
        leaf seconds {
          tailf:cli-drop-node-name;
          type uint8 {
            tailf:info
              "<0-60>  Carrier Transitions delay seconds";
            range "0..60";
          }
        }
        leaf msec {
          tailf:info
            "delay specified in milliseconds";
          type uint16 {
            tailf:info
              "<0-1000>;;Carrier Transitions delay milliseconds";
            range "0..1000";
          }
        }
      }
    }
    container channel-group {
      tailf:info
        "Add this interface to an Etherchannel group";
      tailf:cli-sequence-commands {
        tailf:cli-reset-siblings;
      }
      tailf:cli-compact-syntax;
      leaf number {
        tailf:cli-drop-node-name;
        tailf:cli-incomplete-command;
        type uint16 {
          tailf:info
            "<1-512>;;Channel group number";
          range "1..512";
        }
      }
      leaf mode {
        tailf:info
          "Etherchannel Mode of the interface";
        type enumeration {
          enum "active" {
            tailf:info
              "Enable LACP unconditionally";
          }
          enum "auto" {
            tailf:info
              "Enable PAgP only if a PAgP device is detected";
          }
          enum "desirable" {
            tailf:info
              "Enable PAgP unconditionally";
          }
          enum "on" {
            tailf:info
              "Enable Etherchannel only";
          }
          enum "passive" {
            tailf:info
              "Enable LACP only if a LACP device is detected";
          }
        }
      }
    }
    leaf channel-protocol {
      tailf:info
        "Select the channel protocol (LACP, PAgP)";
      type enumeration {
        enum "lacp" {
          tailf:info
            "Prepare interface for LACP protocol";
        }
        enum "pagp" {
          tailf:info
            "Prepare interface for PAgP protocol";
        }
      }
    }
    container ethernet {
      tailf:info
        "Ethernet interface parameters";
      container oam {
        tailf:info
          "To enable Ethernet Link OAM";
        presence "true";
        leaf max-rate {
          type uint8 {
            tailf:info
              "Maximum number of OAM PDUs sent per second";
            range "1..10";
          }
        }
        leaf min-rate {
          type uint8 {
            tailf:info
              "Minimum transmission rate in seconds";
            range "1..10";
          }
        }
        leaf mode {
          type enumeration {
            enum "active" {
              tailf:info
                "Active OAM client mode";
            }
            enum "passive" {
              tailf:info
                "Passive OAM client mode";
            }
          }
        }
        leaf timeout {
          type uint8 {
            tailf:info
              "OAM client timeout in seconds";
            range "2..30";
          }
        }
      }
    }
    leaf negotiation {
      tailf:info
        "Select autonegotiation mode";
      type enumeration {
        tailf:info
          "Enable link autonegotiation";
        enum "auto";
      }
    }
    leaf duplex {
      tailf:info
        "Configure duplex operation.";
      type enumeration {
        enum "auto" {
          tailf:code-name "duplex_auto";
          tailf:info
            "Enable AUTO duplex configuration";
        }
        enum "full" {
          tailf:code-name "duplex_full";
          tailf:info
            "Force full duplex operation";
        }
        enum "half" {
          tailf:code-name "duplex_half";
          tailf:info
            "Force half-duplex operation";
        }
      }
    }
    leaf speed {
      tailf:info
        "Configure speed operation.";
      type enumeration {
        enum "10" {
          tailf:info
            "Force 10 Mbps operation";
        }
        enum "100" {
          tailf:info
            "Force 100 Mbps operation";
        }
        enum "1000" {
          tailf:info
            "Enable AUTO speed configuration";
        }
        enum "nonegotiate";
        enum "auto" {
          tailf:info
            "Enable AUTO speed configuration";
        }
      }
    }
    container xconnect {
      tailf:info
        "Xconnect commands";
      tailf:cli-sequence-commands;
      tailf:cli-compact-syntax;
      leaf address {
        tailf:cli-drop-node-name;
        tailf:cli-incomplete-command;
        type inet:ipv4-address {
          tailf:info
            "A.B.C.D;;IP address of peer";
        }
      }
      leaf vcid {
        tailf:cli-drop-node-name;
        tailf:cli-incomplete-command;
        type uint32 {
          tailf:info
            "<1-4294967295>;;Enter VC ID value";
          range "1..4294967295";
        }
      }
      leaf encapsulation {
        tailf:info
          "Data encapsulation method";
        tailf:cli-optional-in-sequence;
        type enumeration {
          enum "mpls" {
            tailf:code-name "encap_mpls";
            tailf:info
              "Use MPLS encapsulation";
          }
          enum "l2tpv3" {
            tailf:info
              "Use L2TPv3 encapsulation";
          }
        }
      }
      leaf manual {
        tailf:info
          "Manually configure L2TP session parameters";
        tailf:cli-optional-in-sequence;
        when "../encapsulation = 'l2tpv3'" {
          tailf:xpath-root 3;
        }
        type empty;
      }
      leaf sequence {
        tailf:info
          "Configure sequencing options for xconnect";
        tailf:cli-full-command;
        tailf:cli-optional-in-sequence;
        when "../encapsulation = 'l2tpv3'" {
          tailf:xpath-root 3;
        }
        type enumeration {
          enum "both" {
            tailf:info
              "Transmit and receive sequence numbers";
          }
          enum "receive" {
            tailf:info
              "Receive sequence numbers";
          }
          enum "transmit" {
            tailf:info
              "Transmit sequence numbers";
          }
        }
      }
      leaf pw-class {
        tailf:info
          "Pseudowire-class to use for encapsulation and protocol configuration";
        type string {
          tailf:info
            "WORD;;Pseudowire-class name";
        }
      }
    }
    container pppoe {
      tailf:info
        "pppoe interface subcommands";
      container enable {
        tailf:info
          "Enable pppoe";
        presence "true";
        leaf group {
          tailf:info
            "attach a BBA group";
          type union {
            type string {
              tailf:info
                "WORD;;BBA Group name";
            }
            type enumeration {
              enum "global" {
                tailf:info
                  "Attach global PPPoE group";
              }
            }
          }
        }
      }
      leaf max-sessions {
        tailf:info
          "Maximum PPPOE sessions";
        type uint16 {
          tailf:info
            "<1-4085>;;Maximum PPPOE sessions";
          range "1..4085";
        }
      }
    }
  }

  grouping interface-zone-member-grouping {
    container zone-member {
      tailf:info
        "Apply zone name";
      leaf security {
        tailf:info
          "Security zone";
        type string;
        tailf:non-strict-leafref {
          path "/ncs:devices/ncs:device/ncs:config/ios:zone/security/id" {
            tailf:xpath-root 3;
          }
        }
      }
    }
  }

  grouping interface-pointtopoint-grouping {
    container ppp {
      tailf:info
        "Point-to-Point Protocol";
      leaf accounting {
        tailf:info
          "Set PPP network accounting method";
        type union {
          type string {
            tailf:info
              "WORD;;Named accounting list.";
          }
          type enumeration {
            enum "default" {
              tailf:info
                "The default accounting list.";
            }
          }
        }
      }
      container authentication {
        tailf:info
          "Set PPP link authentication method";
        tailf:cli-compact-syntax;
        tailf:cli-sequence-commands;
        leaf method {
          tailf:cli-drop-node-name;
          type enumeration {
            enum "chap" {
              tailf:info
                "Challenge Handshake Authentication Protocol (CHAP)";
            }
            enum "eap" {
              tailf:info
                "Extensible Authentication Protocol (EAP)";
            }
            enum "ms-chap" {
              tailf:info
                "Microsoft Challenge Handshake Authentication Protocol (MS-CHAP)";
            }
            enum "ms-chap-v2" {
              tailf:info
                "Microsoft CHAP Version 2 (MS-CHAP-V2)";
            }
            enum "pap" {
              tailf:info
                "Password Authentication Protocol (PAP)";
            }
          }
        }
        leaf list-name {
          tailf:cli-break-sequence-commands;
          tailf:cli-drop-node-name;
          type string {
            tailf:info
              "WORD;;Use an authentication list with this name";
          }
          tailf:cli-disallow-value "(callback)|(callin)|(callout)|(default)|(eap)|(ms-chap)|(ms-chap-v2)|(one-time)|(optional)|(pap)";
        }
        leaf chap {
          when "not(../method = 'chap')" {
            tailf:xpath-root 3;
            tailf:dependency "../method";
          }
          tailf:info
            "Challenge Handshake Authentication Protocol (CHAP)";
          type empty;
        }
        leaf callback {
          tailf:info
            "Authenticate remote on callback only";
          type empty;
        }
        leaf callin {
          tailf:info
            "Authenticate remote on incoming call only";
          type empty;
        }
        leaf callout {
          tailf:info
            "Authenticate remote on outgoing call only";
          type empty;
        }
        leaf default {
          tailf:info
            "Use the default authentication list";
          type empty;
        }
        leaf eap {
          when "not(../method = 'eap')" {
            tailf:xpath-root 3;
            tailf:dependency "../method";
          }
          tailf:info
            "Extensible Authentication Protocol (EAP)";
          type empty;
        }
        leaf ms-chap {
          when "not(../method = 'ms-chap')" {
            tailf:xpath-root 3;
            tailf:dependency "../method";
          }
          tailf:info
            "Microsoft Challenge Handshake Authentication Protocol (MS-CHAP)";
          type empty;
        }
        leaf ms-chap-v2 {
          when "not(../method = 'ms-chap-v2')" {
            tailf:xpath-root 3;
            tailf:dependency "../method";
          }
          tailf:info
            "Microsoft CHAP Version 2 (MS-CHAP-V2)";
          type empty;
        }
        leaf one-time {
          tailf:info
            "Allow use of username*OTP for one-time passwords";
          type empty;
        }
        leaf optional {
          tailf:info
            "Allow peer to refuse to authenticate";
          type empty;
        }
        leaf pap {
          when "not(../method = 'pap')" {
            tailf:xpath-root 3;
            tailf:dependency "../method";
          }
          tailf:info
            "Password Authentication Protocol (PAP)";
          type empty;
        }
      }
      leaf authorization {
        tailf:info
          "Set PPP network authorization method";
        type union {
          type string {
            tailf:info
              "WORD;;Named authorization list.";
          }
          type enumeration {
            enum "default" {
              tailf:info
                "The default authorization list.";
            }
          }
        }
      }
      container ipcp {
        tailf:info
          "Set IPCP negotiation options";
        container dns {
          tailf:info
            "Specify DNS negotiation options";
          tailf:cli-compact-syntax;
          tailf:cli-sequence-commands;
          leaf primary {
            tailf:cli-drop-node-name;
            type inet:ipv4-address {
              tailf:info
                "A.B.C.D;;Primary DNS IP address";
            }
          }
        }
      }
      container multilink {
        tailf:info
          "Make interface multilink capable";
        tailf:cli-display-separated;
        presence "true";
        container links {
          tailf:info
            "Specify the limits on the number of links in a bundle";
          container minimum {
            tailf:info
              "Minimum number of links desired in the bundle";
            tailf:cli-compact-syntax;
            tailf:cli-sequence-commands {
              tailf:cli-reset-all-siblings;
            }
            leaf minimum-value {
              tailf:cli-drop-node-name;
              type uint8 {
                tailf:info
                  "<1-255>;;Specify minimum desired number of links in a bundle";
              }
            }
            leaf mandatory {
              tailf:info
                "Disable network layer until minimum number of links is reach";
              type empty;
            }
          }
        }
        leaf group {
          tailf:info
            "Put interface in a multilink bundle";
          type uint32 {
            tailf:info
              "<1-2147483647>;;Multilink group number";
            range "1..2147483647";
          }
        }
        container fragment {
          tailf:info
            "Specify fragmentation parameters";
          container delay {
            tailf:info
              "Specify the maximum delay for each fragment";
            tailf:cli-compact-syntax;
            tailf:cli-sequence-commands {
              tailf:cli-reset-siblings;
            }
            leaf delay-value {
              tailf:cli-drop-node-name;
              type uint16 {
                tailf:info
                  "<0-1000>;;Delay in milliseconds";
                range "0..1000";
              }
            }
            leaf additional-delay-value {
              tailf:cli-drop-node-name;
              type uint16 {
                tailf:info
                  "<1-999>;;Additional delay in microseconds";
                range "1..999";
              }
            }
          }
        }
      }
    }
  }

  grouping crypto-pki-token-grouping {
    container removal {
      tailf:info
        "actions to take after token removal";
      leaf timeout {
        tailf:info
          "seconds after token removal at which keys from the token are cleared";
        type uint16 {
          tailf:info
            "<0-480>;;Token key timeout in seconds";
          range "0..480";
        }
      }
    }
  }

  grouping max-path-grouping {
    container max-path {
      tailf:cli-drop-node-name;
      tailf:cli-compact-syntax;
      tailf:cli-sequence-commands {
        tailf:cli-reset-siblings;
      }
      leaf max {
        tailf:cli-drop-node-name;
        type uint16 {
          range "1..16";
          tailf:info
            "<1-16>;;Number of paths";
        }
        default "1";
      }
      leaf import {
        tailf:info
          "Maximum import paths";
        type uint16 {
          range "1..16";
          tailf:info
            "<1-16>;;Number of import paths";
        }
      }
    }
  }

  grouping metric-route-map-grouping {
    leaf metric {
      tailf:cli-break-sequence-commands;
      tailf:info
        "Metric for redistributed routes";
      type uint32 {
        range "0..4294967295";
        tailf:info
          "<0-4294967295>;;Default metric";
      }
    }
    leaf route-map {
      tailf:info
        "Route map reference";
      type string {
        tailf:info
          "WORD;;Pointer to route-map entries";
      }
    }
  }

  grouping route-map-metric-grouping {
    leaf route-map {
      tailf:info
        "Route map reference";
      type string {
        tailf:info
          "WORD;;Pointer to route-map entries";
      }
    }
    leaf metric {
      tailf:info
        "Metric for redistributed routes";
      type uint32 {
        range "0..4294967295";
        tailf:info
          "<0-4294967295>;;Default metric";
      }
    }
  }

  grouping redistribute-isis-grouping {
    choice osi-ip-choice {
      leaf ip {
        tailf:info
          "Redistribution of IP dynamic routes";
        type empty;
      }
      leaf clns {
        tailf:info
          "Redistribution of OSI dynamic routes";
        type empty;
      }
    }
    leaf routes {
      tailf:cli-drop-node-name;
      type enumeration {
        enum "level-1" {
          tailf:info
            "IS-IS level-1 routes only";
        }
        enum "level-2" {
          tailf:info
            "IS-IS level-2 routes only";
        }
        enum "level-1-2" {
          tailf:info
            "IS-IS level-1 and level-2 routes";
        }
      }
    }
    uses metric-route-map-grouping;
  }

  grouping bgp-address-family-grouping {
    container aggregate-address {
      tailf:info
        "Configure BGP aggregate entries";
      tailf:cli-compact-syntax;
      tailf:cli-sequence-commands {
        tailf:cli-reset-all-siblings;
      }
      leaf address {
        tailf:cli-drop-node-name;
        type inet:ipv4-address {
          tailf:info
            "A.B.C.D;;Aggregate address";
        }
      }
      leaf mask {
        tailf:cli-drop-node-name;
        type inet:ipv4-address {
          tailf:info
            "A.B.C.D;;Aggregate mask";
        }
      }
      leaf advertise-map {
        tailf:cli-break-sequence-commands;
        tailf:info
          "Set condition to advertise attribute";
        type string {
          tailf:info
            "WORD;;Route map to control attribute advertisement";
        }
      }
      leaf as-set {
        tailf:info
          "Generate AS set path information";
        type empty;
      }
      leaf attribute-map {
        type string {
          tailf:info
            "WORD;;Route map for parameter control";
        }
      }
      leaf as-override {
        tailf:info
          "Override matching AS-number while sending update";
        type empty;
      }
      leaf route-map {
        type string {
          tailf:info
            "WORD;;Route map for parameter control";
        }
      }
      leaf summary-only {
        tailf:info
          "Filter more specific routes from updates";
        type empty;
      }
      leaf suppress-map {
        tailf:info
          "Conditionally filter more specific routes from updates";
        type string {
          tailf:info
            "WORD;;Route map for suppression";
        }
      }
    }
    container bgp {
      tailf:info
        "BGP specific commands";
      leaf router-id {
        tailf:cli-full-command;
        tailf:info
          "Override configured router identifier (peers will reset)";
        type inet:ipv4-address {
          tailf:info
            "A.B.C.D;;Manually configured router identifier";
        }
      }
      leaf always-compare-med {
        tailf:info
          "Allow comparing MED from different neighbors";
        tailf:cli-full-command;
        type empty;
      }
      container bestpath {
        tailf:info
          "Change the default bestpath selection";
        leaf compare-routerid {
          tailf:cli-full-command;
          tailf:info
            "Compare router-id for identical EBGP paths";
          type empty;
        }
        container cost-community {
          tailf:info
            "cost community";
          leaf ignore {
            tailf:info
              "Ignore cost communities in bestpath selection";
            type empty;
          }
        }
        container med {
          tailf:info
            "MED attribute";
          choice med-choice {
            container confed {
              tailf:info
                "Compare MED among confederation paths";
              presence "Compare MED among confederation paths";
              leaf missing-at-worst {
                tailf:info
                  "Treat missing MED as the least preferred one";
                type empty;
              }
            }
            leaf missing-at-worst {
              tailf:info
                "Treat missing MED as the least preferred one";
              type empty;
            }
          }
        }
      }
      container client-to-client {
        tailf:info
          "Configure client to client route reflection";
        leaf reflection {
          tailf:info
            "reflection of routes allowed";
          type empty;
        }
      }
      leaf cluster-id {
        tailf:cli-full-command;
        type union {
          type uint32 {
            range "1..4294967295";
            tailf:info
              "<1-4294967295>;;Route-Reflector Cluster-id as 32 bit quantity";
          }
          type inet:ipv4-address {
            tailf:info
              "A.B.C.D;;Route-Reflector Cluster-id in IP address format";
          }
        }
      }
      container confederation {
        tailf:info
          "AS confederation parameters";
        leaf identifier {
          tailf:cli-full-command;
          tailf:info
            "as number";
          type uint16 {
            range "1..65535";
            tailf:info
              "<1-65535>;;Set routing domain confederation AS";
          }
        }
        container peers {
          tailf:info
            "Peer ASs in BGP confederation";
          presence "Peer ASs in BGP confederation";
          leaf-list peers-as {
            tailf:cli-drop-node-name;
            tailf:cli-flat-list-syntax;
            type uint16 {
              range "1..65535";
              tailf:info
                "AS number";
            }
          }
        }
      }
      container dampening {
        tailf:info
          "Enable route-flap dampening";
        presence "enable bgp route-flap dampening";
        choice dampening-choice {
          leaf route-map {
            tailf:info
              "Route-map to specify criteria for dampening";
            type string {
              tailf:info
                "WORD;;route-map name";
            }
          }
          container dampen {
            tailf:cli-drop-node-name;
            tailf:cli-compact-syntax;
            tailf:cli-sequence-commands;
            leaf half-life-time {
              tailf:cli-drop-node-name;
              tailf:cli-incomplete-command;
              type uint8 {
                range "1 .. 45";
                tailf:info
                  "<1-45>;;Half-life time for the penalty";
              }
            }
            leaf reuse-time {
              tailf:cli-drop-node-name;
              tailf:cli-incomplete-command;
              type uint16 {
                range "1 .. 20000";
                tailf:info
                  "<1-20000>;;Value to start reusing a route";
              }
            }
            leaf suppress-time {
              tailf:cli-drop-node-name;
              tailf:cli-incomplete-command;
              type uint16 {
                range "1 .. 20000";
                tailf:info
                  "<1-20000>;;Value to start suppressing a route";
              }
            }
            leaf max-suppress-time {
              tailf:cli-drop-node-name;
              type uint8 {
                range "1 .. 255";
                tailf:info
                  "<1-255>  Maximum duration to suppress a stable route";
              }
            }
          }
        }
      }
      container default {
        tailf:info
          "Configure BGP defaults";
        choice default-choice {
          leaf ipv4-unicast {
            tailf:info
              "Activate ipv4-unicast for a peer by default";
            tailf:cli-boolean-no;
            tailf:cli-trim-default;
            type boolean;
            default "true";
          }
          leaf local-preference {
            tailf:info
              "local preference (higher=more preferred)";
            type uint32 {
              range "1..4294967295";
              tailf:info
                "<0-4294967295>;;Configure default local preference value";
            }
          }
          leaf route-target {
            tailf:info
              "Control behavior based on Route-Target attributes";
            type enumeration {
              enum "filter" {
                tailf:info
                  "Control automatic VPN Route-Target filtering";
              }
            }
          }
        }
      }
      leaf deterministic-med {
        tailf:cli-full-command;
        tailf:info
          "Pick the best-MED path among paths advertised from the neighboring AS";
        type empty;
      }
      leaf dmzlink-bw {
        tailf:cli-full-command;
        tailf:info
          "Use DMZ Link Bandwidth as weight for BGP multipaths";
        type empty;
      }
      leaf enforce-first-as {
        tailf:cli-full-command;
        tailf:info
          "Enforce the first AS for EBGP routes(default)";
        type empty;
      }
      leaf fast-external-fallover {
        tailf:cli-full-command;
        tailf:info
          "Immediately reset session if a link to a directly connected external peer goes down";
        type empty;
      }
      container graceful-restart {
        tailf:info
          "Graceful restart capability parameters";
        presence "Graceful restart capability parameters";
        leaf restart-time {
          tailf:cli-full-command;
          tailf:info
            "Set the max time needed to restart and come back up";
          type uint16 {
            range "1..3600";
            tailf:info
              "<1-3600>;;Delay value (seconds)";
          }
        }
        leaf stalepath-time {
          tailf:info
            "Set the max time to hold onto restarting peer's stale paths";
          type uint16 {
            range "1..3600";
            tailf:info
              "<1-3600>;;Delay value (seconds)";
          }
        }
      }
      list inject-map {
        tailf:info
          "Routemap which specifies prefixes to inject";
        tailf:cli-compact-syntax;
        tailf:cli-sequence-commands;
        tailf:cli-incomplete-command;
        tailf:cli-delete-when-empty;
        key "name";
        leaf name {
          type string {
            tailf:info
              "WORD;;route-map name";
          }
        }
        leaf exist-map {
          tailf:info
            "Routemap which specifies exist condition";
          type string {
            tailf:info
              "WORD;;route-map name";
          }
        }
        leaf copy-attributes {
          tailf:info
            "Copy attributes from aggregate";
          type empty;
        }
      }
      leaf log-neighbor-changes {
        tailf:info
          "Log neighbor up/down and reset reason";
        tailf:cli-full-command;
        type empty;
      }
      leaf maxas-limit {
        tailf:info
          "Allow AS-PATH attribute from any neighbor imposing a limit on number of ASes";
        tailf:cli-full-command;
        type uint16 {
          range "1..2000";
          tailf:info
            "<1-2000>;;Number of ASes in the AS-PATH attribute";
        }
      }
      container nexthop {
        tailf:info
          "Nexthop tracking commands";
        container trigger {
          tailf:info
            "Nexthop triggering";
          leaf delay {
            tailf:cli-full-command;
            tailf:info
              "Set the delay to tigger nexthop tracking";
            type uint8 {
              range "0..100";
              tailf:info
                "<0-100>;;Delay value (seconds)";
            }
          }
          leaf enable {
            tailf:info
              "Enable nexthop tracking";
            tailf:cli-full-command;
            tailf:cli-boolean-no;
            type boolean;
            default "true";
          }
        }
      }
      leaf redistribute-internal {
        tailf:info
          "Allow redistribution of iBGP into IGPs (dangerous)";
        tailf:cli-full-command;
        type empty;
      }
      container regexp {
        tailf:info
          "Select regular expression engine";
        leaf deterministic {
          tailf:info
            "Enable bounded-execution-time regular expression engine";
          type empty;
        }
      }
      leaf scan-time {
        tailf:cli-full-command;
        tailf:info
          "Configure background scanner interval";
        type uint8 {
          range "5..60";
          tailf:info
            "<5-60>;;Scanner interval (seconds)";
        }
      }
      leaf soft-reconfig-backup {
        tailf:info
          "Use soft-reconfiguration inbound only when route-refresh is not negotiated";
        tailf:cli-full-command;
        type empty;
      }
      leaf suppress-inactive {
        tailf:info
          "Suppress routes that are not in the routing table";
        tailf:cli-full-command;
        type empty;
      }
      leaf update-delay {
        tailf:cli-full-command;
        tailf:info
          "Set the max initial delay for sending update";
        type uint16 {
          range "1..3600";
          tailf:info
            "<1-3600>;;Delay value (seconds)";
        }
      }
    }
    container default-information {
      tailf:info
        "Control distribution of default information";
      leaf originate {
        tailf:info
          "Distribute a default route";
        type empty;
      }
    }
    leaf default-metric {
      tailf:info
        "Set metric of redistributed routes";
      tailf:cli-full-command;
      type uint32 {
        range "1..4294967295";
        tailf:info
          "<1-4294967295>;;Default metric";
      }
    }
    container distance {
      tailf:info
        "Define an administrative distance";
      container bgp {
        tailf:info
          "BGP distance";
        tailf:cli-sequence-commands;
        tailf:cli-compact-syntax;
        leaf extern-as {
          tailf:cli-drop-node-name;
          tailf:cli-incomplete-command;
          type uint16 {
            tailf:info
              "<1-255>;;Distance for routes external to the AS";
            range "1..255";
          }
        }
        leaf internal-as {
          tailf:cli-drop-node-name;
          tailf:cli-incomplete-command;
          type uint16 {
            tailf:info
              "<1-255>;;Distance for routes internal to the AS";
            range "1..255";
          }
        }
        leaf local {
          tailf:cli-drop-node-name;
          type uint16 {
            tailf:info
              "<1-255>;;Distance for local routes";
            range "1..255";
          }
        }
      }
      list adm-distance {
        tailf:cli-drop-node-name;
        tailf:cli-suppress-mode;
        tailf:cli-delete-when-empty;
        key "distance srcip wildbits";
        leaf distance {
          type uint16 {
            tailf:info
              "<1-255>;;Administrative distance";
            range "1..255";
          }
        }
        leaf srcip {
          type inet:ipv4-address {
            tailf:info
              "A.B.C.D;;IP Source address";
          }
        }
        leaf wildbits {
          type inet:ipv4-address {
            tailf:info
              "A.B.C.D;;Wildcard bits";
          }
        }
        leaf acl {
          tailf:cli-drop-node-name;
          type union {
            type uint16 {
              range "1..99" {
                tailf:info
                  "<1-99>;;IP Standard access list number";
              }
            }
            type uint16 {
              range "1300..1999" {
                tailf:info
                  "<1300-1999>;;IP Standard expanded access list number";
              }
            }
            type string {
              pattern '[a-zA-Z].*';
              tailf:info
                "WORD;;Standard access-list name";
            }
          }
        }
      }
    }
    list distribute-list {
      tailf:info
        "Filter networks in routing updates";
      tailf:cli-compact-syntax;
      tailf:cli-suppress-mode;
      tailf:cli-delete-when-empty;
      key "id";
      leaf id {
        tailf:cli-incomplete-command;
        type bgp-distribute-list-type;
      }
      choice in-out-choice {
        container in {
          presence "enable incoming routing updates";
          tailf:info
            "Filter incoming routing updates";
          leaf interface {
            type string;
          }
        }
        container out {
          presence "enable outgoing routing updates";
          tailf:info
            "Filter outgoing routing updates";
          leaf interface {
            type string;
          }
        }
      }
    }
    container maximum-paths {
      tailf:info
        "Forward packets over multiple paths";
      choice max-path-choice {
        case eibgp-case {
          container eibgp {
            tailf:info
              "Both eBGP and iBGP paths as multipath";
            uses max-path-grouping;
          }
        }
        case ibgp-case {
          container ibgp {
            tailf:info
              "iBGP-multipath";
            choice ibgp-choice {
              case a {
                container unequal-cost {
                  tailf:info
                    "Perform Un-Equal cost multipath selection";
                  uses max-path-grouping;
                }
              }
              case b {
                uses max-path-grouping;
              }
            }
          }
        }
        case none-case {
          uses max-path-grouping;
        }
        case import-case {
          leaf import {
            tailf:info
              "Maximum import paths";
            type uint16 {
              range "1..16";
              tailf:info
                "<1-16>;;Number of import paths";
            }
          }
        }
      }
    }
    list neighbor {
      tailf:info
        "Specify a neighbor router";
      tailf:cli-suppress-mode;
      tailf:cli-delete-when-empty;
      tailf:cli-incomplete-command;
      ordered-by user;
      must 'count(*) > 1' {
        tailf:xpath-root 3;
        tailf:dependency ".";
      }
      key "id";
      leaf id {
        type union {
          type string {
            tailf:info
              "WORD;;Neighbor tag";
          }
          type inet:ipv4-address {
            tailf:info
              "A.B.C.D;;Neighbor address";
          }
          type inet:ipv6-address {
            tailf:info
              "X:X:X:X::X;;Neighbor IPv6 address";
          }
        }
      }
      container peer-group {
        tailf:info
          "Member of the peer-group";
        tailf:cli-delete-when-empty;
        presence "true";
        leaf peer-group-name {
          tailf:info
            "WORD;;peer-group name";
          tailf:cli-drop-node-name;
          tailf:cli-delete-container-on-delete;
          tailf:cli-full-command;
          type string;
        }
      }
      leaf remote-as {
        tailf:info
          "Specify a BGP neighbor";
        tailf:cli-full-command;
        tailf:cli-delete-container-on-delete;
        type uint16 {
          tailf:info
            "<1-65535>  AS of remote neighbor";
          range "1..65535";
        }
      }
      container local-as {
        tailf:info
          "Specify a local-as number";
        tailf:cli-compact-syntax;
        tailf:cli-sequence-commands {
          tailf:cli-reset-siblings;
        }
        tailf:cli-delete-when-empty;
        presence "Specify a local-as number";
        leaf as-no {
          tailf:cli-drop-node-name;
          type uint16 {
            range "1..65535";
            tailf:info
              "<1-65535>;;AS number used as local AS";
          }
        }
        leaf no-prepend {
          tailf:info
            "Do not prepend local-as to updates from ebgp peers";
          type empty;
        }
        leaf replace-as {
          tailf:info
            "Replace real AS with local AS in the EBGP updates";
          type empty;
        }
        leaf dual-as {
          tailf:info
            "Accept either real AS or local AS from the ebgp peer";
          type empty;
        }
      }
      leaf activate {
        tailf:info
          "Enable the Address Family for this Neighbor";
        tailf:cli-full-command;
        type empty;
      }
      leaf advertisement-interval {
        tailf:info
          "Minimum interval between sending BGP routing updates";
        tailf:cli-full-command;
        type uint16 {
          range "0..600";
          tailf:info
            "<0-600>;;time in seconds";
        }
      }
      container allowas-in {
        tailf:info
          "Accept as-path with my AS present in it";
        presence "accept as-paths";
        tailf:cli-delete-when-empty;
        leaf as-number {
          tailf:cli-drop-node-name;
          type uint8 {
            range "1..10";
            tailf:info
              "<1-10>  Number of occurances of AS number";
          }
        }
      }
      container as-override {
        tailf:info
          "Override matching AS-number while sending update";
        tailf:cli-delete-when-empty;
        presence "true";
        leaf disable {
          type empty;
        }
      }
      container capability {
        tailf:info
          "Advertise capability to the peer";
        container orf {
          tailf:info
            "Advertise ORF capability to the peer";
          leaf-list prefix-list {
            tailf:cli-flat-list-syntax;
            tailf:info
              "Advertise prefixlist ORF capability to this neighbor";
            max-elements 1;
            type enumeration {
              enum "both" {
                tailf:info
                  "Capability to SEND and RECEIVE the ORF to/from this neighbor";
              }
              enum "receive" {
                tailf:info
                  "Capability to RECEIVE the ORF from this neighbor";
              }
              enum "send" {
                tailf:info
                  "Capability to SEND the ORF to this neighbor";
              }
            }
          }
        }
      }
      container default-originate {
        tailf:info
          "Originate default route to this neighbour";
        tailf:cli-delete-when-empty;
        presence "enable originate default route to this neighbour";
        leaf route-map {
          tailf:info
            "Route-map to specify criteria to originate default";
          type string {
            tailf:info
              "WORD;;route-map name";
          }
        }
      }
      leaf description {
        tailf:info
          "Neighbor specific description";
        tailf:cli-full-command;
        tailf:cli-multi-value;
        type string {
          tailf:info
            "LINE;;Up to 80 characters describing this neighbor";
        }
      }
      leaf disable-connected-check {
        tailf:info
          "One-hop away EBGP peer using loopback address";
        tailf:cli-full-command;
        type empty;
      }
      list distribute-list {
        tailf:info
          "Filter updates to/from this neighbor";
        tailf:cli-suppress-mode;
        tailf:cli-delete-when-empty;
        key "inout";
        leaf inout {
          type enumeration {
            enum "in" {
              tailf:code-name "dist_in";
              tailf:info
                "Filter incoming updates";
            }
            enum "out" {
              tailf:code-name "dist_out";
              tailf:info
                "Filter outgoing updates";
            }
          }
        }
        leaf accesslist {
          tailf:cli-drop-node-name;
          tailf:cli-prefix-key;
          type bgp-distribute-list-type2;
          mandatory true;
        }
      }
      leaf dmzlink-bw {
        tailf:info
          "Propagate the DMZ link bandwidth";
        tailf:cli-full-command;
        type empty;
      }
      container ebgp-multihop {
        tailf:info
          "Allow EBGP neighbors not on directly connected networks";
        tailf:cli-delete-when-empty;
        presence "Allow EBGP neighbors not on directly connected networks";
        leaf max-hop {
          tailf:cli-drop-node-name;
          type uint8 {
            range "1..255";
            tailf:info
              "<1-255>;;maximum hop count";
          }
        }
      }
      leaf fall-over {
        tailf:info
          "session fall on peer route lost";
        tailf:cli-full-command;
        type empty;
      }
      list filter-list {
        tailf:info
          "Establish BGP filters";
        tailf:cli-suppress-mode;
        tailf:cli-delete-when-empty;
        key "inout";
        leaf inout {
          type enumeration {
            enum "in" {
              tailf:code-name "filter_in";
              tailf:info
                "Filter incoming routes";
            }
            enum "out" {
              tailf:code-name "filter_out";
              tailf:info
                "Filter outgoing routes";
            }
          }
        }
        leaf as-path-list {
          tailf:cli-drop-node-name;
          tailf:cli-prefix-key;
          type uint16 {
            range "1..500";
            tailf:info
              "<1-500>;;AS path access list";
          }
          mandatory true;
        }
      }
      container inherit {
        tailf:info
          "Inherit a template";
        leaf peer-policy {
          tailf:info
            "Inherit a peer-policy template";
          tailf:cli-full-command;
          type string {
            tailf:info
              "WORD;;Template name";
          }
        }
        leaf peer-session {
          tailf:info
            "Inherit a peer-session template";
          tailf:cli-full-command;
          type string {
            tailf:info
              "WORD;;Template name";
          }
        }
      }
      container maximum-prefix {
        tailf:info
          "Maximum number of prefixes accepted from this peer";
        tailf:cli-compact-syntax;
        tailf:cli-sequence-commands {
          tailf:cli-reset-all-siblings;
        }
        leaf max-prefix-no {
          tailf:cli-drop-node-name;
          type uint32 {
            range "1..2147483647";
            tailf:info
              "<1-2147483647>;;maximum no. of prefix limit";
          }
        }
        leaf threshold {
          tailf:cli-drop-node-name;
          tailf:cli-break-sequence-commands;
          type uint8 {
            range "1..100";
            tailf:info
              "<1-100>;;Threshold value (%) at which to generate a warning msg";
          }
        }
        leaf restart {
          tailf:cli-full-command;
          tailf:info
            "Restart bgp connection after limit is exceeded";
          type uint16 {
            range "1..65535";
            tailf:info
              "<1-65535>  Restart interval in minutes";
          }
        }
        leaf warning-only {
          tailf:cli-full-command;
          tailf:info
            "Only give warning message when limit is exceeded";
          type empty;
        }
      }
      leaf next-hop-self {
        tailf:cli-full-command;
        tailf:info
          "Disable the next hop calculation for this neighbor";
        type empty;
      }
      leaf next-hop-unchanged {
        tailf:cli-full-command;
        tailf:info
          "Propagate the iBGP paths's next hop unchanged for this neighbor";
        type empty;
      }
      container password {
        tailf:info
          "Set a password";
        tailf:cli-compact-syntax;
        leaf enctype {
          tailf:cli-drop-node-name;
          tailf:cli-incomplete-command;
          tailf:cli-reset-container;
          type uint8 {
            range "0..7";
            tailf:info
              "<0-7>;;Encryption type (0 to disable encryption, 7 for proprietary)";
          }
          default "0";
        }
        leaf text {
          tailf:cli-drop-node-name;
          tailf:cli-full-command;
          tailf:cli-multi-value;
          tailf:cli-reset-container;
          type string {
            tailf:info
              "LINE;;The password";
          }
        }
      }
      list prefix-list {
        tailf:info
          "Filter updates to/from this neighbor";
        tailf:cli-suppress-mode;
        tailf:cli-delete-when-empty;
        key "inout";
        leaf inout {
          type enumeration {
            enum "in" {
              tailf:code-name "prefix_in";
              tailf:info
                "Filter incoming updates";
            }
            enum "out" {
              tailf:code-name "prefix_out";
              tailf:info
                "Filter outgoing updates";
            }
          }
        }
        leaf prefix-list-name {
          tailf:cli-drop-node-name;
          tailf:cli-prefix-key;
          type string {
            tailf:info
              "WORD;;Name of a prefix list";
          }
          mandatory true;
        }
      }
      leaf remove-private-as {
        tailf:cli-full-command;
        tailf:info
          "Remove private AS number from outbound updates";
        type empty;
      }
      list route-map {
        tailf:info
          "Apply route map to neighbor";
        tailf:cli-suppress-mode;
        tailf:cli-delete-when-empty;
        key "inout";
        leaf inout {
          type enumeration {
            enum "in" {
              tailf:code-name "route_in";
              tailf:info
                "Apply map to incoming routes";
            }
            enum "out" {
              tailf:code-name "route_out";
              tailf:info
                "Apply map to outbound routes";
            }
          }
        }
        leaf route-map-name {
          tailf:cli-drop-node-name;
          tailf:cli-prefix-key;
          type string {
            tailf:info
              "WORD;;Name of route map";
          }
          mandatory true;
        }
      }
      leaf route-reflector-client {
        tailf:cli-full-command;
        tailf:info
          "Configure a neighbor as Route Reflector client";
        type empty;
      }
      container send-community {
        tailf:info
          "Send Community attribute to this neighbor";
        tailf:cli-delete-when-empty;
        presence "true";
        leaf send-community-where {
          tailf:cli-drop-node-name;
          type enumeration {
            enum "both" {
              tailf:info
                "Send Standard and Extended Community attributes";
            }
            enum "extended" {
              tailf:info
                "Send Extended Community attribute";
            }
            enum "standard" {
              tailf:code-name "send_standard";
              tailf:info
                "Send Standard Community attribute";
            }
          }
        }
      }
      container send-label {
        tailf:info
          "Send NLRI + MPLS Label to this peer";
        leaf send-label-explicit {
          tailf:cli-drop-node-name;
          type enumeration {
            enum "explicit-null" {
              tailf:code-name "send_explicit_null";
              tailf:info
                "Advertise Explicit Null label in place of Implicit Null";
            }
          }
        }
      }
      leaf shutdown {
        tailf:cli-full-command;
        tailf:info
          "Administratively shut down this neighbor";
        type empty;
      }
      leaf soft-reconfiguration {
        tailf:cli-full-command;
        tailf:info
          "Per neighbor soft reconfiguration";
        type enumeration {
          enum "inbound" {
            tailf:info
              "Allow inbound soft reconfiguration for this neighbor";
          }
        }
      }
      container timers {
        tailf:info
          "BGP per neighbor timers";
        tailf:cli-compact-syntax;
        tailf:cli-sequence-commands {
          tailf:cli-reset-siblings;
        }
        leaf keepalive-interval {
          tailf:cli-drop-node-name;
          tailf:cli-incomplete-command;
          type uint16 {
            range "0..65535";
            tailf:info
              "<0-65535>;;Keepalive interval";
          }
        }
        leaf holdtime {
          tailf:cli-drop-node-name;
          type uint16 {
            range "0..65535";
            tailf:info
              "<0-65535>;;Holdtime";
          }
        }
        leaf minimum-neighbor-hold {
          tailf:cli-drop-node-name;
          type uint16 {
            range "0..65535";
            tailf:info
              "<0-65535>  Minimum hold time from neighbor";
          }
        }
      }
      container translate-update {
        tailf:info
          "Translate Update to MBGP format";
        container ipv4 {
          tailf:info
            "Address Family";
          container multicast {
            tailf:info
              "Address Family modifier";
            tailf:cli-delete-when-empty;
            presence "Address Family modifier";
            leaf unicast {
              tailf:info
                "Address Family modifier";
              type empty;
            }
          }
        }
      }
      container transport {
        tailf:info
          "Transport options";
        leaf connection-mode {
          tailf:info
            "Specify passive or active connection";
          type enumeration {
            enum "active" {
              tailf:info
                "Actively establish the TCP session";
            }
            enum "passive" {
              tailf:info
                "Passively establish the TCP session";
            }
          }
        }
      }
      container ttl-security {
        tailf:info
          "BGP ttl security check";
        leaf hops {
          tailf:info
            "IP hops";
          type uint8 {
            range "1..254";
            tailf:info
              "<1-254>;;maximum number of hops";
          }
        }
      }
      leaf unsuppress-map {
        tailf:info
          "Route-map to selectively unsuppress suppressed routes";
        tailf:cli-full-command;
        type string {
          tailf:info
            "WORD;;Name of route map";
        }
      }
      container update-source {
        tailf:info
          "Source of routing updates";
        tailf:cli-diff-dependency "/ios:interface" {
          tailf:xpath-root 3;
        }
        uses interface-grouping;
      }
      leaf version {
        tailf:cli-full-command;
        tailf:info
          "Set the BGP version to match a neighbor";
        type uint16 {
          range "4";
          tailf:info
            "<4-4>;;Neighbor's BGP version";
        }
      }
      leaf weight {
        tailf:cli-full-command;
        tailf:info
          "Set default weight for routes from this neighbor";
        type uint16 {
          range "0..65535";
          tailf:info
            "<0-65535>;;default weight";
        }
      }
      container ha-mode {
        tailf:info
          "high availability mode";
        container graceful-restart {
          tailf:info
            "graceful-restart for this peer";
          presence "true";
          leaf disable {
            tailf:info
              "disable graceful-restart";
            type empty;
          }
        }
        container sso {
          tailf:info
            "stateful-switchover support for this peer";
          presence "true";
          leaf disable {
            tailf:info
              "disable stateful-switchover";
            type empty;
          }
        }
      }
    }
    list network {
      tailf:info
        "Specify a network to announce via BGP";
      tailf:cli-suppress-mode;
      tailf:cli-delete-when-empty;
      tailf:cli-compact-syntax;
      tailf:cli-reset-container;
      key "number";
      leaf number {
        type inet:ipv4-address {
          tailf:info
            "A.B.C.D;;Network number";
        }
      }
      leaf backdoor {
        tailf:info
          "Specify a BGP backdoor route";
        tailf:cli-full-command;
        type empty;
      }
      leaf mask {
        tailf:info
          "Network mask";
        type inet:ipv4-address {
          tailf:info
            "A.B.C.D;;Network mask";
        }
      }
      leaf route-map {
        tailf:info
          "Route-map to modify the attributes";
        type string {
          tailf:info
            "WORD;;Name of the route map";
        }
      }
    }
    container redistribute {
      tailf:info
        "Redistribute information from another routing protocol";
      container bgp {
        tailf:info
          "Border Gateway Protocol (BGP)";
        tailf:cli-compact-syntax;
        tailf:cli-sequence-commands {
          tailf:cli-reset-all-siblings;
        }
        leaf as-no {
          tailf:cli-drop-node-name;
          type uint16 {
            range "1..65535";
            tailf:info
              "<1-65535>;;Autonomous system number";
          }
        }
        uses metric-route-map-grouping;
      }
      container connected {
        tailf:info
          "Connected";
        tailf:cli-delete-when-empty;
        presence "Connected";
        uses metric-route-map-grouping;
      }
      container dvmrp {
        tailf:info
          "Redistribution of DVMRP into BGP IPv4 Multicast";
        tailf:cli-compact-syntax;
        tailf:cli-sequence-commands {
          tailf:cli-reset-siblings;
        }
        tailf:cli-delete-when-empty;
        presence "Redistribution of DVMRP into BGP IPv4 Multicast";
        uses route-map-metric-grouping;
      }
      container eigrp {
        tailf:info
          "Enhanced Interior Gateway Routing Protocol (EIGRP)";
        tailf:cli-compact-syntax;
        tailf:cli-sequence-commands {
          tailf:cli-reset-all-siblings;
        }
        leaf as-no {
          tailf:cli-drop-node-name;
          type uint16 {
            range "1..65535";
            tailf:info
              "<1-65535>;;Autonomous system number";
          }
        }
        uses metric-route-map-grouping;
      }
      container isis {
        tailf:info
          "ISO IS-IS";
        list isis-area {
          tailf:cli-drop-node-name;
          key "name";
          leaf name {
            type string {
              tailf:info
                "WORD;;ISO routing area tag";
              pattern '^([^mlir].*)|(i[^p].*)|(ip..*)|(l[^e].*)|(le[^v].*)|(lev[^e].*)|(leve[^l].*)|(level[^\-].*)|(m[^e].*)|(me[^t].*)|(met[^r].*)|(metr[^i].*)|(metri[^c].*)|(metric..*)*(r[^o].*)|(ro[^u].*)|(rou[^t].*)|(rout[^e].*)|(route[^\-].*)|(route-[^m].*)|(route-m[^a].*)|(route-ma[^p].*)|(route-map..*)$';
            }
          }
          uses redistribute-isis-grouping;
        }
        container default {
          tailf:cli-drop-node-name;
          uses redistribute-isis-grouping;
        }
      }
      container iso-igrp {
        tailf:info
          "IGRP for OSI networks";
        list iso-igrp-area {
          tailf:cli-compact-syntax;
          tailf:cli-sequence-commands;
          tailf:cli-drop-node-name;
          key "name";
          leaf name {
            type string {
              tailf:info
                "WORD;;Pointer to route-map entries";
              pattern '^([^r].*)|(r^[o].*)|(ro[^u].*)|(rou[^t].*)|(rout[^e].*)|(route[^\-].*)|(route-[^m].*)|(route-m[^a].*)|(route-ma[^p])|(route-map..*)';
            }
          }
          uses route-map-metric-grouping;
        }
        container default {
          tailf:cli-compact-syntax;
          tailf:cli-sequence-commands;
          uses route-map-metric-grouping;
        }
      }
      container mobile {
        presence "Mobile routes";
        tailf:info
          "Mobile routes";
        uses metric-route-map-grouping;
      }
      container odr {
        presence "On Demand stub Routes";
        tailf:info
          "On Demand stub Routes";
        uses metric-route-map-grouping;
      }
      list ospf {
        tailf:info
          "Open Shortest Path First (OSPF)";
        key "id";
        leaf id {
          type uint16 {
            range "1..65535";
            tailf:info
              "<1-65535>;;Process ID";
          }
        }
        list vrf {
          tailf:info
            "VPN Routing/Forwarding Instance";
          tailf:cli-diff-dependency "/ios:ip/vrf" {
            tailf:xpath-root 3;
          }
          tailf:cli-diff-dependency "/ios:vrf/definition" {
            tailf:xpath-root 3;
          }
          key "name";
          leaf name {
            type string {
              tailf:info
                "WORD;;VPN Routing/Forwarding Instance (VRF) name";
            }
          }
          container match {
            tailf:info
              "Redistribution of OSPF routes";
          }
          uses metric-route-map-grouping;
        }
        container non-vrf {
          tailf:cli-drop-node-name;
          container match {
            tailf:info
              "Redistribution of OSPF routes";
          }
          uses metric-route-map-grouping;
        }
      }
      container rip {
        presence "Routing Information Protocol (RIP)";
        tailf:info
          "Routing Information Protocol (RIP)";
        uses metric-route-map-grouping;
      }
      container static {
        presence "Static routes";
        tailf:info
          "Static routes";
        uses metric-route-map-grouping;
      }
    }
    leaf synchronization {
      tailf:info
        "Perform IGP synchronization";
      tailf:cli-full-command;
      type empty;
    }
    leaf auto-summary {
      tailf:info
        "Enable automatic network number summarization";
      tailf:cli-boolean-no;
      tailf:cli-trim-default;
      tailf:cli-full-command;
      type boolean;
      default "false";
    }
    leaf table-map {
      tailf:info
        "Map external entry attributes into routing table";
      tailf:cli-full-command;
      type string {
        tailf:info
          "WORD;;route-map name";
      }
    }
    container timers {
      tailf:info
        "Adjust routing timers";
      tailf:cli-compact-syntax;
      tailf:cli-sequence-commands {
        tailf:cli-reset-siblings;
      }
      leaf keepalive-interval {
        tailf:cli-drop-node-name;
        tailf:cli-incomplete-command;
        type uint16 {
          range "0..65535";
          tailf:info
            "<0-65535>;;Keepalive interval";
        }
      }
      leaf holdtime {
        tailf:cli-drop-node-name;
        type uint16 {
          range "0..65535";
          tailf:info
            "<0-65535>;;Holdtime";
        }
      }
      leaf minimum-neighbor-hold {
        tailf:cli-drop-node-name;
        type uint16 {
          range "0..65535";
          tailf:info
            "<0-65535>  Minimum hold time from neighbor";
        }
      }
    }
  }

  grouping ospf-ospfv3-common-address-family-grouping {
    container default-information {
      tailf:info
        "Control distribution of default information";
      container originate {
        tailf:info
          "Distribute a default route";
        presence "Distribute a default route";
        leaf always {
          tailf:info
            "Always advertise default route";
          type empty;
        }
        leaf metric {
          tailf:info
            "OSPF default metric";
          type uint32 {
            range "0 .. 16777214";
            tailf:info
              "<0-16777214>;;OSPF metric";
          }
          tailf:cli-no-value-on-delete;
        }
        leaf metric-type {
          tailf:info
            "OSPF metric type for default routes";
          type ospf-metric-type;
          tailf:cli-no-value-on-delete;
        }
        leaf route-map {
          tailf:info
            "Route map reference";
          type string {
            tailf:info
              "WORD;;Route map name";
          }
          tailf:cli-no-value-on-delete;
        }
      }
    }
    leaf default-metric {
      tailf:info
        "Set metric of redistributed routes";
      tailf:cli-full-command;
      type uint32 {
        range "1 .. 16777214";
        tailf:info
          "<1-16777214>;;OSPF default metric";
      }
    }
    container discard-route {
      tailf:info
        "Enable or disable discard-route installation";
      presence "Enable or disable discard-route installation";
      tailf:cli-compact-syntax;
      leaf external {
        tailf:info
          "Discard route for redistributed summarised routes";
        type uint32 {
          range "1 .. 255";
          tailf:info
            "<1-255>;;Administrative distance for redistributed summarised routes";
        }
      }
      leaf internal {
        tailf:info
          "Discard route for summarised internal routes";
        type uint32 {
          range "1 .. 255";
          tailf:info
            "<1-255>;;Administrative distance for summarised internal routes";
        }
      }
    }
    container distance {
      tailf:cli-compact-syntax;
      tailf:info
        "Define an administrative distance";
      container ospf-distance {
        tailf:cli-compact-syntax;
        tailf:cli-drop-node-name;
        leaf distance {
          tailf:cli-drop-node-name;
          type uint32 {
            range "1 .. 255";
            tailf:info
              "<1-255>;;OSPF Administrative distance";
          }
        }
        tailf:cli-sequence-commands;
        leaf ip {
          tailf:cli-drop-node-name;
          tailf:cli-incomplete-command;
          type inet:ipv4-address {
            tailf:info
              "A.B.C.D;;IP source address";
          }
        }
        leaf wildcard {
          tailf:cli-drop-node-name;
          type inet:ipv4-address {
            tailf:info
              "A.B.C.D;;Wildcard bits";
          }
        }
        leaf acl-name {
          tailf:cli-drop-node-name;
          type access-list-standard-id-type;
          tailf:cli-no-value-on-delete;
        }
      }
      container ospf {
        tailf:info
          "OSPF routes Administrative distance";
        leaf external {
          tailf:info
            "External routes";
          type uint32 {
            range "1 .. 255";
            tailf:info
              "<1-255>;;Distance for external routes";
          }
          tailf:cli-suppress-no;
          tailf:cli-no-value-on-delete;
          tailf:cli-no-name-on-delete;
        }
        leaf inter-area {
          tailf:info
            "Inter-area routes";
          type uint32 {
            range "1 .. 255";
            tailf:info
              "<1-255>;;Distance for inter-area routes";
          }
          tailf:cli-suppress-no;
          tailf:cli-no-name-on-delete;
          tailf:cli-no-value-on-delete;
        }
        leaf intra-area {
          tailf:info
            "Intra-area routes";
          type uint32 {
            range "1 .. 255";
            tailf:info
              "<1-255>;;Distance for intra-area routes";
          }
          tailf:cli-suppress-no;
          tailf:cli-no-name-on-delete;
          tailf:cli-no-value-on-delete;
        }
      }
    }
    leaf maximum-paths {
      tailf:info
        "Forward packets over multiple paths";
      tailf:cli-full-command;
      type uint32 {
        range "1 .. 32";
        tailf:info
          "<1-32>;;Number of paths";
      }
    }
    container redistribute {
      tailf:info
        "Redistribute information from another routing protocol";
      uses ospf-redistribute-grouping;
      container bgp {
        tailf:info
          "Border Gateway Protocol (BGP)";
        tailf:cli-sequence-commands;
        uses ospf-redistribute-bgp-grouping;
      }
      container connected {
        tailf:info
          "Connected";
        presence "Connected";
        uses ospf-redistribute-grouping;
      }
      container eigrp {
        tailf:info
          "Enhanced Interior Gateway Routing Protocol (EIGRP)";
        tailf:cli-sequence-commands;
        uses ospf-redistribute-bgp-grouping;
      }
      container isis {
        presence "ISO IS-IS";
        tailf:info
          "ISO IS-IS";
        choice isis-level-routes-isis-area-choice {
          leaf isis-level-routes {
            tailf:cli-drop-node-name;
            type enumeration {
              enum "level-1" {
                tailf:info
                  "IS-IS level-1 routes only";
              }
              enum "level-2" {
                tailf:info
                  "IS-IS level-2 routes only";
              }
              enum "level-1-2" {
                tailf:info
                  "IS-IS level-1 and level-2 routes";
              }
            }
          }
          list isis-area {
            tailf:cli-suppress-mode;
            tailf:cli-delete-when-empty;
            tailf:cli-drop-node-name;
            key "name";
            leaf name {
              tailf:cli-disallow-value "level-1|level-2|level-1-2|metric|metric-type|route-map|subnets|tag";
              type string {
                tailf:info
                  "WORD;;ISO routing area tag";
              }
            }
            uses ospf-redistribute-grouping;
          }
        }
        uses ospf-redistribute-grouping;
      }
      container iso-igrp {
        tailf:info
          "IGRP for OSI networks";
        presence "IGRP for OSI networks";
        tailf:cli-sequence-commands;
        choice area-tag-route-map-choice {
          container area-tag-route-map-container {
            tailf:cli-drop-node-name;
            tailf:cli-flatten-container;
            tailf:cli-sequence-commands;
            leaf area-tag {
              tailf:cli-drop-node-name;
              tailf:cli-disallow-value "route-map";
              type string {
                tailf:info
                  "WORD;;ISO routing area tag";
              }
            }
            leaf route-map {
              tailf:info
                "Route map reference";
              type string {
                tailf:info
                  "WORD;;Pointer to route-map entries";
              }
            }
          }
          leaf route-map {
            tailf:info
              "Route map reference";
            type string {
              tailf:info
                "WORD;;Pointer to route-map entries";
            }
          }
        }
        container iso-igrp-container {
          tailf:cli-drop-node-name;
          tailf:cli-compact-syntax;
          uses ospf-iso-igrp-redistribute-grouping;
        }
      }
      container maximum-prefix {
        tailf:info
          "Maximum number of prefixes redistributed to protocol";
        tailf:cli-sequence-commands;
        tailf:cli-compact-syntax;
        leaf number {
          tailf:cli-drop-node-name;
          type uint32 {
            range "1 .. 4294967295";
            tailf:info
              "<1-4294967295>;;Maximum number of IP prefixes redistributed";
          }
        }
        container threshold-warning-only-container {
          tailf:cli-compact-syntax;
          tailf:cli-drop-node-name;
          leaf threshold {
            tailf:cli-drop-node-name;
            type uint32 {
              range "1 .. 100";
              tailf:info
                "<1-100>;;Threshold value (%) at which to generate a warning message";
            }
          }
          leaf warning-only {
            tailf:info
              "Only give warning message when limit is exceeded";
            tailf:cli-full-command;
            type empty;
          }
        }
      }
      container mobile {
        tailf:info
          "Mobile routes";
        presence "Mobile routes";
        uses ospf-redistribute-grouping;
      }
      container odr {
        tailf:info
          "On Demand stub Routes";
        presence "On Demand stub Routes";
        uses ospf-redistribute-grouping;
      }
      list ospf {
        tailf:info
          "Open Shortest Path First (OSPF)";
        tailf:cli-suppress-mode;
        tailf:cli-delete-when-empty;
        key "id";
        leaf id {
          tailf:cli-suppress-range;
          type uint32 {
            range "1 .. 65535";
            tailf:info
              "<1-65535>;;Process ID";
          }
        }
        container match {
          tailf:cli-compact-syntax;
          tailf:cli-flatten-container;
          tailf:info
            "Redistribution of OSPF routes";
          container internal {
            presence "Redistribute OSPF internal routes";
            tailf:info
              "Redistribute OSPF internal routes";
            tailf:cli-compact-syntax;
            tailf:cli-flatten-container;
            uses ospf-redistribute-match-grouping;
          }
          container external {
            tailf:info
              "Redistribute OSPF external routes";
            presence "Redistribute OSPF external routes";
            tailf:cli-compact-syntax;
            tailf:cli-flatten-container;
            leaf external-routes {
              tailf:cli-drop-node-name;
              type redist-ospf-external-type;
            }
            uses ospf-redistribute-match-grouping;
          }
          container nssa-external {
            tailf:info
              "Redistribute OSPF NSSA external routes";
            presence "Redistribute OSPF NSSA external routes";
            tailf:cli-compact-syntax;
            tailf:cli-flatten-container;
            leaf nssa-external-routes {
              tailf:cli-drop-node-name;
              type redist-ospf-external-type;
            }
            uses ospf-redistribute-match-grouping;
          }
        }
        uses ospf-redistribute-grouping;
        leaf vrf {
          tailf:info
            "VPN Routing/Forwarding Instance";
          tailf:cli-diff-dependency "/ios:ip/vrf" {
            tailf:xpath-root 3;
          }
          tailf:cli-diff-dependency "/ios:vrf/definition" {
            tailf:xpath-root 3;
          }
          type string {
            tailf:info
              "WORD;;VPN Routing/Forwarding Instance (VRF) name";
          }
        }
      }
      container rip {
        tailf:info
          "Routing Information Protocol (RIP)";
        presence "Routing Information Protocol (RIP)";
        uses ospf-redistribute-grouping;
      }
      container static {
        tailf:info
          "Static routes";
        presence "Static routes";
        uses ospf-redistribute-grouping;
      }
    }
  }

  grouping ospf-ospfv3-common-grouping {
    list area {
      tailf:info
        "OSPF area parameters";
      tailf:cli-suppress-mode;
      tailf:cli-delete-when-empty;
      tailf:cli-incomplete-command;
      key "id";
      leaf id {
        tailf:cli-suppress-range;
        type ospf-area-type;
      }
      container authentication {
        tailf:info
          "Enable authentication";
        presence "true";
        leaf message-digest {
          tailf:info
            "Use message-digest authentication";
          type empty;
        }
      }
      leaf default-cost {
        tailf:info
          "Set the summary default-cost of a NSSA/stub area";
        tailf:cli-full-command;
        tailf:cli-no-value-on-delete;
        type uint32 {
          range "0 .. 16777215";
          tailf:info
            "<0-16777215;;Stub's advertised external route metric";
        }
      }
      list filter-list {
        tailf:info
          "Filter networks between OSPF areas";
        tailf:cli-suppress-mode;
        tailf:cli-delete-when-empty;
        tailf:cli-compact-syntax;
        key "in-out";
        leaf prefix {
          tailf:cli-prefix-key;
          mandatory true;
          tailf:info
            "Filter prefixes between OSPF areas";
          type string {
            tailf:info
              "WORD;;Name of an IP prefix-list";
          }
        }
        leaf in-out {
          type enumeration {
            enum "in" {
              tailf:info
                "Filter networks sent to this area";
            }
            enum "out" {
              tailf:info
                "Filter networks sent from this area";
            }
          }
        }
      }
      container nssa {
        tailf:info
          "Specify a NSSA area";
        presence "Specify a NSSA area";
        container default-information-originate {
          tailf:cli-flatten-container;
          tailf:info
            "Originate Type 7 default into NSSA area";
          presence "Originate Type 7 default into NSSA area";
          leaf metric {
            tailf:info
              "OSPF default metric";
            type int32 {
              range "0 .. 16777214";
              tailf:info
                "<0-16777214>;;OSPF metric";
            }
            tailf:cli-no-value-on-delete;
            tailf:cli-no-name-on-delete;
            tailf:cli-suppress-no;
          }
          leaf metric-type {
            tailf:info
              "OSPF metric type for default routes";
            type ospf-metric-type;
          }
        }
        leaf no-ext-capability {
          tailf:info
            "Do not send domain specific capabilities into NSSA";
          type empty;
        }
        leaf no-redistribution {
          tailf:info
            "No redistribution into this NSSA area";
          type empty;
        }
        leaf no-summary {
          tailf:info
            "Do not send summary LSA into NSSA";
          type empty;
        }
        container translate {
          tailf:info
            "Translate LSA";
          container type7 {
            tailf:info
              "From Type 7 to Type 5";
            leaf suppress-fa {
              tailf:info
                "Suppress forwarding address in translated LSAs";
              type empty;
            }
          }
        }
      }
      list range {
        tailf:info
          "Summarize routes matching address/mask (border routers only)";
        tailf:cli-suppress-mode;
        tailf:cli-delete-when-empty;
        key "ip mask";
        leaf ip {
          type inet:ipv4-address {
            tailf:info
              "A.B.C.D;;IP address to match";
          }
        }
        leaf mask {
          type inet:ipv4-address {
            tailf:info
              "A.B.C.D;;IP mask for address";
          }
        }
        choice advertise-choice {
          leaf advertise {
            tailf:info
              "Advertise this range (default)";
            type empty;
          }
          leaf not-advertise {
            tailf:info
              "DoNotAdvertise this range";
            type empty;
          }
        }
        leaf cost {
          tailf:info
            "User specified metric for this range";
          tailf:cli-full-command;
          type uint32 {
            range "0 .. 16777215";
            tailf:info
              "<0-16777215>;;Advertised metric for this range";
          }
        }
      }
      list sham-link {
        tailf:info
          "Define a sham link and its parameters";
        tailf:cli-suppress-mode;
        tailf:cli-delete-when-empty;
        key "source dest";
        leaf source {
          type inet:ipv4-address {
            tailf:info
              "A.B.C.D;;IP addr associated with sham-link source";
          }
        }
        leaf dest {
          type inet:ipv4-address {
            tailf:info
              "A.B.C.D;;IP addr associated with sham-link destination";
          }
        }
        leaf cost {
          tailf:info
            "Associate a cost with the sham-link";
          type uint16 {
            range "0 .. 65535";
            tailf:info
              "<1-65535>;;Cost of the sham-link";
          }
        }
      }
      container stub {
        tailf:info
          "Specify a stub area";
        presence "Specify a stub area";
        leaf no-ext-capability {
          tailf:info
            "Do not send domain specific capabilities into stub area";
          type empty;
        }
        leaf no-summary {
          tailf:info
            "Do not send summary LSA into stub area";
          tailf:cli-full-command;
          type empty;
        }
      }
      list virtual-link {
        tailf:info
          "Define a virtual link and its parameters";
        tailf:cli-suppress-mode;
        tailf:cli-delete-when-empty;
        key "id";
        leaf id {
          type inet:ipv4-address {
            tailf:info
              "A.B.C.D;;ID (IP addr) associated with virtual link neighbor";
          }
        }
        leaf authentication {
          tailf:info
            "Set authentication type";
          type empty;
        }
        container authentication-key {
          tailf:info
            "Set authentication key";
          leaf auth-type {
            tailf:cli-drop-node-name;
            type uint8 {
              range "0 .. 7";
              tailf:info
                "<0-7>;;Encryption type (0 for not yet encrypted, 7 for proprietary)";
            }
          }
          leaf auth-key {
            tailf:cli-drop-node-name;
            tailf:cli-full-command;
            type string {
              length "1 .. 8";
              tailf:info
                "WORD;;Authentication key (8 chars)";
            }
          }
        }
        leaf dead-interval {
          tailf:info
            "Dead router detection time";
          tailf:cli-no-value-on-delete;
          type uint16 {
            range "1 .. 8192";
            tailf:info
              "<1-8192;;Seconds>";
          }
        }
        leaf hello-interval {
          tailf:info
            "Hello packet interval";
          tailf:cli-no-value-on-delete;
          type int32 {
            range "1 .. 8192";
            tailf:info
              "<1-8192;;Seconds>";
          }
        }
        list message-digest-key {
          tailf:info
            "Set message digest key";
          tailf:cli-suppress-mode;
          tailf:cli-delete-when-empty;
          tailf:cli-incomplete-command;
          key "id";
          leaf id {
            tailf:cli-suppress-range;
            type uint8 {
              range "1 .. 255";
              tailf:info
                "<1-255>;;Key ID";
            }
          }
          container md5 {
            tailf:info
              "Use MD5 algorithm";
            tailf:cli-sequence-commands;
            leaf auth-type {
              tailf:cli-drop-node-name;
              tailf:cli-optional-in-sequence;
              type uint8 {
                range "0 .. 7";
                tailf:info
                  "<0-7>;;Encryption type (0 for not yet encrypted, 7 for proprietary)";
              }
            }
            leaf auth-key {
              tailf:cli-drop-node-name;
              type string {
                length "1 .. 16";
                tailf:info
                  "WORD;;Authentication key (16 chars)";
              }
            }
          }
        }
        leaf retransmit-interval {
          tailf:info
            "LSA retransmit interval";
          type uint16 {
            range "1 .. 8192";
            tailf:info
              "<1-8192>;;Seconds";
          }
          tailf:cli-no-value-on-delete;
        }
        leaf transmit-delay {
          tailf:info
            "LSA transmission delay";
          type uint16 {
            range "1 .. 8192";
            tailf:info
              "<1-8192>;;Seconds";
          }
          tailf:cli-no-value-on-delete;
        }
      }
    }
    container auto-cost {
      tailf:info
        "Calculate OSPF interface cost according to bandwidth";
      presence "Calculate OSPF interface cost according to bandwidth";
      leaf reference-bandwidth {
        tailf:info
          "Use reference bandwidth method to assign OSPF cost";
        type uint32 {
          tailf:info
            "<1-4294967>;;The reference bandwidth in terms of Mbits per second";
          range "1 .. 4294967";
        }
      }
    }
    container bfd {
      tailf:info
        "BFD configuration commands";
      leaf all-interfaces {
        tailf:info
          "Enable BFD on all interfaces";
        type empty;
      }
    }
    container interface-id {
      tailf:info
        "Source of the interface ID";
      leaf snmp-if-index {
        tailf:info
          "SNMP MIB ifIndex";
        type empty;
      }
    }
    container log-adjacency-changes {
      tailf:info
        "Log changes in adjacency state";
      presence "true";
      leaf detail {
        tailf:info
          "Log all state changes";
        type empty;
      }
    }
    container max-lsa {
      tailf:info
        "maximum number of LSAs OSPF process will receive";
      tailf:cli-sequence-commands;
      leaf number {
        tailf:cli-drop-node-name;
        type uint32 {
          range "1 .. 4294967294";
          tailf:info
            "<1-4294967294>;;Maximum number of non self-generated LSAs this process can receive";
        }
      }
      container options {
        tailf:cli-drop-node-name;
        tailf:cli-compact-syntax;
        leaf threshold-value {
          tailf:cli-drop-node-name;
          type uint32 {
            range "1 .. 100";
            tailf:info
              "<1-100>;;Threshold value (%) at which to generate a warning msg";
          }
        }
        leaf ignore-count {
          tailf:info
            "maximum number of times adjacencies can be suppressed";
          type uint32 {
            range "1 .. 65534";
            tailf:info
              "<1-65534>;;count on how many times adjacencies can be suppressed";
          }
        }
        leaf ignore-time {
          tailf:info
            "time during which all adjacencies are suppressed";
          type uint32 {
            range "1 .. 17895";
            tailf:info
              "<1-17895>;;number of minutes during which all adjacencies are suppressed";
          }
        }
        leaf reset-time {
          tailf:info
            "time after which ignore-count is reset to zero";
          type uint32 {
            range "2 .. 35791";
            tailf:info
              "<2-35791>;;number of minutes after which ignore-count is reset to zero";
          }
        }
        leaf warning-only {
          tailf:info
            "Only give warning message when limit is exceeded";
          tailf:cli-full-command;
          type empty;
        }
      }
    }
    uses passive-interface-grouping;
    container queue-depth {
      tailf:info
        "OSPF Hello/Router process queue depth";
      container hello {
        tailf:info
          "OSPF Hello process queue depth";
        uses queue-depth-grouping;
      }
      container update {
        tailf:info
          "OSPF Router process queue depth";
        uses queue-depth-grouping;
      }
    }
    container timers {
      tailf:info
        "Adjust routing timers";
      container lsa {
        tailf:info
          "OSPF LSA timers";
        leaf arrival {
          tailf:info
            "OSPF LSA arrival timer";
          type uint32 {
            range "0 .. 600000";
            tailf:info
              "<0-600000>;;The minimum interval in milliseconds between accepting the same LSA";
          }
        }
      }
      container pacing {
        tailf:info
          "OSPF pacing timers";
        leaf flood {
          tailf:info
            "OSPF flood pacing timer";
          tailf:cli-full-command;
          type uint32 {
            range "5 .. 100";
            tailf:info
              "<5-100>;;The minimum interval in msec to pace limit flooding on interface";
          }
        }
        leaf lsa-group {
          tailf:info
            "OSPF LSA group pacing timer";
          tailf:cli-full-command;
          type uint32 {
            range "10 .. 1800";
            tailf:info
              "<10-1800>;;Interval in sec between group of LSA being refreshed or maxaged";
          }
        }
        leaf retransmission {
          tailf:info
            "OSPF retransmission pacing timer";
          tailf:cli-full-command;
          type uint32 {
            range "5 .. 200";
            tailf:info
              "<5-200>;;The minimum interval in msec between neighbor retransmissions";
          }
        }
      }
      container throttle {
        tailf:info
          "OSPF throttle timers";
        container lsa {
          tailf:info
            "OSPF LSA throttle timers";
          container all {
            tailf:info
              "For all type of OSPF LSAs";
            tailf:cli-sequence-commands;
            tailf:cli-compact-syntax;
            leaf delay {
              tailf:cli-drop-node-name;
              tailf:cli-incomplete-command;
              type uint32 {
                range "0 .. 600000";
                tailf:info
                  "<0-600000>;;Delay to generate first occurrence of LSA in milliseconds";
              }
            }
            leaf min-delay {
              tailf:cli-drop-node-name;
              tailf:cli-incomplete-command;
              type uint32 {
                range "0 .. 600000";
                tailf:info
                  "<0-600000>;;Minimum delay between originating the same LSA in milliseconds";
              }
            }
            leaf max-delay {
              tailf:cli-drop-node-name;
              type uint32 {
                range "0 .. 600000";
                tailf:info
                  "<0-600000>;;Maximum delay between originating the same LSA in milliseconds";
              }
            }
          }
        }
        container spf {
          tailf:info
            "OSPF SPF throttle timers";
          tailf:cli-sequence-commands;
          tailf:cli-compact-syntax;
          leaf delay {
            tailf:cli-drop-node-name;
            tailf:cli-incomplete-command;
            type uint32 {
              range "0 .. 600000";
              tailf:info
                "<0-600000>;;Delay between receiving a change to SPF calculation in milliseconds";
            }
          }
          leaf min-delay {
            tailf:cli-drop-node-name;
            tailf:cli-incomplete-command;
            type uint32 {
              range "0 .. 600000";
              tailf:info
                "<0-600000>;;Delay between first and second SPF calculation in milliseconds";
            }
          }
          leaf max-delay {
            tailf:cli-drop-node-name;
            type uint32 {
              range "0 .. 600000";
              tailf:info
                "<0-600000>;;Maximum wait time in milliseconds for SPF calculations";
            }
          }
        }
      }
    }
    leaf router-id {
      tailf:cli-full-command;
      tailf:info
        "Override configured router identifier (peers will reset)";
      type inet:ipv4-address {
        tailf:info
          "A.B.C.D;;Manually configured router identifier";
      }
    }
  }

  grouping ospfv3-address-family-grouping;

  grouping queue-depth-grouping {
    leaf options {
      tailf:cli-drop-node-name;
      tailf:cli-full-command;
      tailf:cli-trim-default;
      type union {
        type uint32 {
          range "1 .. 2147483647";
          tailf:info
            "<1-2147483647>;;maximum numer of packets in the queue";
        }
        type enumeration {
          enum "unlimited" {
            tailf:info
              "Unlimited queue depth";
          }
        }
      }
      default "unlimited";
    }
  }

  grouping ospf-redistribute-match-grouping {
    leaf metric {
      tailf:info
        "Metric for redistributed routes";
      type uint32 {
        tailf:info
          "<0-16777214>;;OSPF default metric";
      }
    }
    leaf subnets {
      tailf:info
        "Consider subnets for redistribution into OSPF";
      type empty;
    }
    leaf route-map {
      tailf:info
        "Route map reference";
      type string {
        tailf:info
          "WORD;;Pointer to route-map entries";
      }
    }
    leaf tag {
      tailf:info
        "Set tag for routes redistributed into OSPF";
      type uint32 {
        range "0 .. 4294967295";
        tailf:info
          "<0-4294967295>;;32-bit tag value";
      }
    }
  }

  grouping ospf-iso-igrp-redistribute-grouping {
    leaf metric {
      tailf:info
        "Metric for redistributed routes";
      type uint32 {
        tailf:info
          "<0-16777214>;;OSPF default metric";
      }
    }
    leaf metric-type {
      tailf:info
        "OSPF/IS-IS exterior metric type for redistributed routes";
      type enumeration {
        enum "1" {
          tailf:info
            "Set OSPF External Type 1 metrics";
        }
        enum "2" {
          tailf:info
            "Set OSPF External Type 2 metrics";
        }
      }
    }
    leaf tag {
      tailf:info
        "Set tag for routes redistributed into OSPF";
      type uint32 {
        range "0 .. 4294967295";
        tailf:info
          "<0-4294967295>;;32-bit tag value";
      }
    }
    leaf subnets {
      tailf:info
        "Consider subnets for redistribution into OSPF";
      type empty;
    }
  }

  grouping ospf-redistribute-grouping {
    container redist-options {
      tailf:cli-drop-node-name;
      tailf:cli-compact-syntax;
      uses ospf-iso-igrp-redistribute-grouping;
      leaf route-map {
        tailf:info
          "Route map reference";
        type string {
          tailf:info
            "WORD;;Pointer to route-map entries";
        }
      }
    }
  }

  grouping ospf-redistribute-bgp-grouping {
    leaf as-number {
      tailf:cli-drop-node-name;
      type uint32 {
        range "1 .. 65535";
        tailf:info
          "<1-65535>;;Autonomous system number";
      }
    }
    uses ospf-redistribute-grouping;
  }

  grouping router-rip-grouping {
    uses address-family-vrf-grouping;
    leaf flash-update-threshold {
      tailf:info
        "Specify flash update threshold in second";
      tailf:cli-full-command;
      type uint8 {
        range "0 .. 30";
        tailf:info
          "<0-30>;;threshold in seconds";
      }
    }
    leaf input-queue {
      tailf:info
        "Specify input queue depth";
      tailf:cli-full-command;
      type uint16 {
        range "0 .. 1024";
        tailf:info
          "0-1024;;queue depth";
      }
    }
    leaf output-delay {
      tailf:info
        "Interpacket delay for RIP updates";
      tailf:cli-full-command;
      type uint8 {
        range "8 .. 50";
        tailf:info
          "8-50;;Delay in milliseconds";
      }
    }
    uses passive-interface-grouping;
    container traffic-share {
      tailf:info
        "How to compute traffic share over alternate paths";
      container min {
        tailf:info
          "All traffic shared among min metric paths";
        leaf across-interfaces {
          tailf:info
            "Use different interfaces for equal-cost paths";
          type empty;
        }
      }
    }
  }

  grouping default-redistribute-grouping {
    container connected {
      presence "Connected";
      tailf:info
        "Connected";
      uses rip-metric-route-map-grouping;
    }
    list bgp {
      tailf:info
        "Border Gateway Protocol (BGP)";
      tailf:cli-suppress-mode;
      tailf:cli-delete-when-empty;
      key "as-number";
      leaf as-number {
        type uint16 {
          range "1 .. 65535";
          tailf:info
            "<1-65535>;;Autonomous system number";
        }
      }
      uses rip-metric-route-map-grouping;
    }
    list eigrp {
      tailf:info
        "Enhanced Interior Gateway Routing Protocol (EIGRP)";
      tailf:cli-suppress-mode;
      tailf:cli-delete-when-empty;
      key "as-number";
      leaf as-number {
        type uint16 {
          range "1 .. 65535";
          tailf:info
            "<1-65535>;;Autonomous system number";
        }
      }
      uses rip-metric-route-map-grouping;
    }
    container isis {
      presence "ISO IS-IS";
      tailf:info
        "ISO IS-IS";
      list isis-area {
        tailf:cli-suppress-mode;
        tailf:cli-delete-when-empty;
        tailf:cli-drop-node-name;
        key "name";
        leaf name {
          tailf:cli-disallow-value "level-1|level-2|level-1-2|metric|route-map";
          type string {
            tailf:info
              "WORD;;ISO routing area tag";
          }
        }
        uses redist-isis-grouping;
      }
      uses redist-isis-grouping;
    }
    container iso-igrp {
      presence "IGRP for OSI networks";
      tailf:info
        "IGRP for OSI networks";
      list isoigrp-list {
        tailf:info
          "Border Gateway Protocol (BGP)";
        tailf:cli-suppress-mode;
        tailf:cli-delete-when-empty;
        tailf:cli-drop-node-name;
        key "iso-area-tag";
        leaf iso-area-tag {
          tailf:cli-disallow-value "route-map";
          type string {
            tailf:info
              "WORD;;ISO routing area tag";
          }
        }
        uses rip-iso-igrp-metric-route-map-grouping;
      }
      uses rip-iso-igrp-metric-route-map-grouping;
    }
    container mobile {
      presence "Mobile routes";
      tailf:info
        "Mobile routes";
      uses rip-metric-route-map-grouping;
    }
    container odr {
      presence "On Demand stub Routes";
      tailf:info
        "On Demand stub Routes";
      uses rip-metric-route-map-grouping;
    }
    list ospf {
      tailf:info
        "Open Shortest Path First (OSPF)";
      tailf:cli-suppress-mode;
      tailf:cli-delete-when-empty;
      key "process-id";
      leaf process-id {
        tailf:cli-suppress-range;
        type uint16 {
          range "1 .. 65535";
          tailf:info
            "<1-65535>;;Process ID";
        }
      }
      list vrf {
        tailf:info
          "VPN Routing/Forwarding Instance";
        tailf:cli-diff-dependency "/ios:ip/vrf" {
          tailf:xpath-root 3;
        }
        tailf:cli-diff-dependency "/ios:vrf/definition" {
          tailf:xpath-root 3;
        }
        key "name";
        leaf name {
          type string {
            tailf:info
              "WORD;;VPN Routing/Forwarding Instance (VRF) name";
          }
        }
      }
      container match {
        tailf:cli-compact-syntax;
        tailf:cli-flatten-container;
        tailf:info
          "Redistribution of OSPF routes";
        container internal {
          presence "Redistribute OSPF internal routes";
          tailf:info
            "Redistribute OSPF internal routes";
          tailf:cli-compact-syntax;
          tailf:cli-flatten-container;
          uses rip-metric-route-map-grouping;
        }
        container external {
          tailf:info
            "Redistribute OSPF external routes";
          presence "Redistribute OSPF external routes";
          tailf:cli-compact-syntax;
          tailf:cli-flatten-container;
          leaf external-routes {
            tailf:cli-drop-node-name;
            type redist-ospf-external-type;
          }
          uses rip-metric-route-map-grouping;
        }
        container nssa-external {
          tailf:info
            "Redistribute OSPF NSSA external routes";
          presence "Redistribute OSPF NSSA external routes";
          tailf:cli-compact-syntax;
          tailf:cli-flatten-container;
          leaf nssa-external-routes {
            tailf:cli-drop-node-name;
            type redist-ospf-external-type;
          }
          uses rip-metric-route-map-grouping;
        }
      }
      uses rip-metric-route-map-grouping;
    }
    container static {
      presence "Static routes";
      tailf:info
        "Static routes";
      uses rip-metric-route-map-grouping;
    }
    container rip {
      presence "Routing Information Protocol (RIP)";
      tailf:info
        "Routing Information Protocol (RIP)";
      uses rip-metric-route-map-grouping;
    }
  }

  grouping distance-grouping {
    container distance {
      tailf:cli-compact-syntax;
      tailf:info
        "Define an administrative distance";
      leaf distance-leaf {
        tailf:cli-drop-node-name;
        tailf:cli-full-command;
        type uint8 {
          range "1..255";
          tailf:info
            "1-255;;Administrative distance";
        }
      }
      list distance-list {
        tailf:cli-suppress-mode;
        tailf:cli-delete-when-empty;
        tailf:cli-drop-node-name;
        key "number ip mask";
        leaf number {
          tailf:cli-suppress-range;
          type uint8 {
            range "1 .. 255";
            tailf:info
              "1-255;;Administrative distance";
          }
        }
        leaf ip {
          type inet:ipv4-address {
            tailf:info
              "A.B.C.D;;IP source address";
          }
        }
        leaf mask {
          type inet:ipv4-address {
            tailf:info
              "A.B.C.D;;Wildcard bits";
          }
        }
      }
    }
  }

  grouping offset-list-grouping {
    list offset-list {
      tailf:info
        "Add or subtract offset from RIP metrics";
      tailf:cli-compact-syntax;
      tailf:cli-suppress-mode;
      tailf:cli-delete-when-empty;
      tailf:cli-suppress-list-no;
      tailf:cli-sequence-commands;
      key "in-out";
      leaf in-out {
        tailf:cli-incomplete-command;
        type offset-list-in-out-type;
      }
      leaf offset {
        tailf:cli-drop-node-name;
        mandatory true;
        type uint8 {
          range "0 .. 16";
          tailf:info
            "<0-16>;;Offset";
        }
      }
    }
  }

  grouping default-router-rip-grouping {
    leaf auto-summary {
      tailf:info
        "Enable automatic network number summarization";
      type empty;
    }
    leaf maximum-paths {
      tailf:cli-full-command;
      tailf:info
        "Forward packets over multiple paths";
      type uint8 {
        range "1 .. 32";
        tailf:info
          "1-32;;Number of paths";
      }
    }
    list neighbor {
      tailf:info
        "Specify a neighbor router";
      tailf:cli-suppress-mode;
      tailf:cli-delete-when-empty;
      key "ip";
      leaf ip {
        type inet:ipv4-address;
        tailf:info
          "A.B.C.D;;Neighbor address";
      }
    }
    list network {
      tailf:info
        "Enable routing on an IP network";
      tailf:cli-suppress-mode;
      tailf:cli-delete-when-empty;
      key "ip";
      leaf ip {
        type inet:ipv4-address;
        tailf:info
          "A.B.C.D;;Network number";
      }
    }
    leaf validate-update-source {
      tailf:info
        "Perform sanity checks against source address of routing updates";
      tailf:cli-full-command;
      tailf:cli-boolean-no;
      tailf:cli-trim-default;
      type boolean;
      default "true";
    }
  }

  grouping address-family-vrf-grouping {
    uses default-router-rip-grouping;
    container default-information {
      tailf:cli-incomplete-no;
      tailf:info
        "Control distribution of default information";
      container originate {
        tailf:cli-full-no;
        presence "Distribute a default route";
        tailf:info
          "Distribute a default route";
        leaf route-map {
          tailf:info
            "Route-map reference";
          tailf:cli-no-value-on-delete;
          type string {
            tailf:info
              "WORD;;Route map name";
          }
        }
      }
    }
    leaf default-metric {
      tailf:info
        "Set metric of redistributed routes";
      tailf:cli-full-command;
      type uint32 {
        range "1..4294967295";
        tailf:info
          "<1-4294967295>;;Default metric";
      }
    }
    uses distance-grouping;
    uses distribute-list-grouping;
    uses offset-list-grouping;
    container redistribute {
      tailf:info
        "Redistribute information from another routing protocol";
      uses rip-metric-route-map-grouping;
      uses default-redistribute-grouping;
    }
    container timers {
      tailf:info
        "Adjust routing timers";
      tailf:cli-incomplete-no;
      tailf:cli-compact-syntax;
      container basic {
        tailf:info
          "Basic routing protocol update timers";
        tailf:cli-sequence-commands;
        tailf:cli-full-no;
        leaf updates {
          tailf:cli-drop-node-name;
          tailf:cli-incomplete-command;
          tailf:cli-no-value-on-delete;
          type uint32 {
            range "1 .. 4294967295";
            tailf:info
              "1-4294967295;;Interval between updates for RIP";
          }
        }
        leaf invalid {
          tailf:cli-drop-node-name;
          tailf:cli-incomplete-command;
          tailf:cli-no-value-on-delete;
          type uint32 {
            range "1 .. 4294967295";
            tailf:info
              "1-4294967295;;Invalid";
          }
        }
        leaf holddown {
          tailf:cli-drop-node-name;
          tailf:cli-incomplete-command;
          tailf:cli-no-value-on-delete;
          type uint32 {
            range "1 .. 4294967295";
            tailf:info
              "1-4294967295;;Holddown";
          }
        }
        leaf flush {
          tailf:cli-drop-node-name;
          tailf:cli-incomplete-command;
          tailf:cli-no-value-on-delete;
          type uint32 {
            range "1 .. 4294967295";
            tailf:info
              "1-4294967295;;Flush";
          }
        }
        leaf sleep {
          tailf:cli-drop-node-name;
          tailf:cli-no-value-on-delete;
          type uint32 {
            range "1 .. 4294967295";
            tailf:info
              "1-4294967295;;Sleep time, in milliseconds";
          }
        }
      }
    }
    leaf version {
      tailf:info
        "Set routing protocol version";
      type uint8 {
        range "1 .. 2";
        tailf:info
          "1-2;;rip version 1 or 2";
      }
    }
  }

  grouping redist-isis-grouping {
    container rip-isis-redist {
      tailf:cli-drop-node-name;
      leaf isis-level-routes {
        tailf:cli-drop-node-name;
        type enumeration {
          enum "level-1" {
            tailf:info
              "IS-IS level-1 routes only";
          }
          enum "level-2" {
            tailf:info
              "IS-IS level-2 routes only";
          }
          enum "level-1-2" {
            tailf:info
              "IS-IS level-1 and level-2 routes";
          }
        }
      }
      uses rip-metric-route-map-grouping;
    }
  }

  grouping rip-metric-route-map-grouping {
    container rip-metric-route-map {
      tailf:cli-drop-node-name;
      tailf:cli-compact-syntax;
      container metric {
        tailf:cli-compact-syntax;
        tailf:cli-flatten-container;
        tailf:info
          "Metric for redistributed routes";
        choice metric-transparent-choice {
          leaf metric-value {
            tailf:cli-drop-node-name;
            tailf:info
              "Metric for redistributed routes";
            type uint32 {
              range "0 .. 16";
              tailf:info
                "<0-16>;;Default metric";
            }
          }
          leaf transparent {
            tailf:info
              "Transparently redistribute metric";
            type empty;
          }
        }
      }
      leaf route-map {
        tailf:info
          "Route map reference";
        type string {
          tailf:info
            "WORD;;Pointer to route-map entries";
        }
      }
    }
  }

  grouping rip-iso-igrp-metric-route-map-grouping {
    container rip-metric-route-map {
      tailf:cli-drop-node-name;
      tailf:cli-compact-syntax;
      tailf:cli-sequence-commands;
      leaf route-map {
        tailf:info
          "Route map reference";
        type string {
          tailf:info
            "WORD;;Pointer to route-map entries";
        }
      }
      container metric {
        tailf:cli-compact-syntax;
        tailf:info
          "Metric for redistributed routes";
        choice metric-transparent-choice {
          leaf metric-value {
            tailf:cli-drop-node-name;
            tailf:info
              "Metric for redistributed routes";
            type uint32 {
              range "0 .. 16";
              tailf:info
                "<0-16>;;Default metric";
            }
          }
          leaf transparent {
            tailf:info
              "Transparently redistribute metric";
            type empty;
          }
        }
      }
    }
  }

  grouping narrow-wide-transition-grouping {
    leaf narrow-wide {
      tailf:cli-drop-node-name;
      tailf:cli-full-command;
      type isis-level-type;
    }
    leaf transition {
      tailf:info
        "Accept both styles of TLVs during transition";
      type isis-level-type;
      tailf:cli-full-command;
    }
  }

  grouping spf-intervals-grouping {
    leaf interval {
      tailf:cli-drop-node-name;
      type uint32 {
        range "1 .. 120";
        tailf:info
          "<1-120>;;Interval between consecutive SPFs in seconds";
      }
    }
    leaf initial-wait {
      tailf:cli-drop-node-name;
      type uint32 {
        range "1 .. 120000";
        tailf:info
          "<1-120000>;;Initial wait before first SPF in milliseconds";
      }
    }
    leaf minimum-wait {
      tailf:cli-drop-node-name;
      type uint32 {
        range "1 .. 120000";
        tailf:info
          "<1-120000>;;Minimum wait between first and second SPF in milliseconds";
      }
    }
  }

  grouping authenticate-snp-grouping {
    leaf authenticate {
      tailf:info
        "Authentication";
      tailf:cli-incomplete-command;
      type empty;
    }
    leaf snp {
      tailf:info
        "SNP PDUs";
      type enumeration {
        enum "send-only" {
          tailf:info
            "Send but do not check PDUs on receiving";
        }
        enum "validate" {
          tailf:info
            "Send and check PDUs on receiving";
        }
      }
    }
  }

  grouping lsp-gen-interval-grouping {
    leaf interval {
      tailf:cli-drop-node-name;
      type uint32 {
        range "1 .. 120";
        tailf:info
          "<1-120>;;Interval in seconds";
      }
    }
    leaf initial-wait {
      tailf:cli-drop-node-name;
      type uint32 {
        range "1 .. 120000";
        tailf:info
          "<1-120000>;;Initial wait in milliseconds";
      }
    }
    leaf wait {
      tailf:cli-drop-node-name;
      type uint32 {
        range "1 .. 120000";
        tailf:info
          "<1-120000>;;Wait between first and second lsp generation in milliseconds";
      }
    }
  }

  grouping set-overload-bit-suppress-grouping {
    leaf external {
      tailf:info
        "If overload-bit set, don't advertise IP prefixes learned from other protocols";
      tailf:cli-break-sequence-commands;
      type empty;
    }
    leaf interlevel {
      tailf:info
        "If overload-bit set, don't advertise IP prefixes learned from another ISIS level";
      type empty;
    }
  }

  grouping summary-address-metric-tag-grouping {
    leaf metric {
      tailf:info
        "Set metric for summay route";
      tailf:cli-full-command;
      type uint32 {
        range "1 .. 4294967295";
        tailf:info
          "<1-4294967295>;;metric";
      }
    }
    leaf tag {
      tailf:info
        "Set tag";
      type uint32 {
        range "1 .. 4294967295";
        tailf:info
          "<1-4294967295>;;32-bit tag value";
      }
    }
  }

  grouping authentication-level-grouping {
    leaf levels {
      tailf:cli-drop-node-name;
      type authentication-level-type;
    }
  }

  grouping redist-level-grouping {
    leaf levels {
      tailf:cli-drop-node-name;
      tailf:cli-break-sequence-commands;
      type isis-routes-level-type;
    }
  }

  grouping isis-redist-container-content-grouping {
    uses redist-level-grouping;
    leaf metric {
      tailf:info
        "ISIS default metric";
      type uint32 {
        range "0 .. 4294967295";
        tailf:info
          "<0-4294967295>;;ISIS default metric";
      }
    }
    leaf metric-type {
      tailf:info
        "OSPF/IS-IS exterior metric type for redistributed routes";
      type enumeration {
        enum "external" {
          tailf:info
            "Set IS-IS External metric type";
        }
        enum "internal" {
          tailf:info
            "Set IS-IS Internal metric type";
        }
      }
    }
    leaf route-map {
      tailf:info
        "Route map reference";
      type string {
        tailf:info
          "WORD;;Pointer to route-map entries";
      }
    }
  }

  grouping isis-redist-grouping {
    container isis-redist-container {
      tailf:cli-drop-node-name;
      uses isis-redist-container-content-grouping;
    }
  }

  grouping isis-redist-af-grouping {
    container isis-redist-af-container {
      tailf:cli-drop-node-name;
      leaf include-connected {
        tailf:info
          "Include connected";
        type empty;
      }
      uses isis-redist-container-content-grouping;
    }
  }

  grouping isis-redist-ospf-match-grouping {
    uses redist-level-grouping;
    leaf metric {
      tailf:info
        "ISIS default metric";
      type uint32 {
        range "0 .. 4294967295";
        tailf:info
          "<0-4294967295>;;ISIS default metric";
      }
    }
    leaf route-map {
      tailf:info
        "Route map reference";
      type string {
        tailf:info
          "WORD;;Pointer to route-map entries";
      }
    }
  }

  grouping isis-redist-clns-ip-grouping {
    uses isis-redist-grouping;
    container clns {
      tailf:info
        "Redistribution of BGP NSAP routes";
      presence "Redistribution of BGP NSAP routes";
      leaf route-map {
        tailf:info
          "Route map reference";
        type string {
          tailf:info
            "WORD;;Pointer to route-map entries";
        }
      }
    }
    leaf ip {
      tailf:info
        "Redistribution of BGP IP routes";
      type empty;
    }
  }

  grouping isis-address-family-grouping {
    leaf adjacency-check {
      tailf:info
        "Check ISIS neighbor protocol support";
      type empty;
      tailf:cli-full-command;
    }
    container default-information {
      tailf:cli-incomplete-no;
      tailf:info
        "Control distribution of default information";
      container originate {
        tailf:cli-full-no;
        presence "Distribute a default route";
        tailf:info
          "Distribute a default route";
        leaf route-map {
          tailf:info
            "Route-map reference";
          tailf:cli-no-value-on-delete;
          type string {
            tailf:info
              "WORD;;Route map name";
          }
        }
      }
    }
    leaf maximum-paths {
      tailf:info
        "Forward packets over multiple paths";
      tailf:cli-full-command;
      type uint32 {
        range "1 .. 32";
        tailf:info
          "<1-32>;;Number of paths";
      }
    }
    container metric {
      tailf:info
        "Set ISIS metric for all interfaces";
      tailf:cli-compact-syntax;
      tailf:cli-sequence-commands;
      leaf default {
        tailf:cli-drop-node-name;
        type uint32 {
          range "1 .. 63";
          tailf:info
            "<1-63>;;Default metric";
        }
      }
      leaf level-1-2 {
        tailf:cli-drop-node-name;
        type enumeration {
          enum "level-1" {
            tailf:info
              "Apply metric to level-1 links";
          }
          enum "level-2" {
            tailf:info
              "Apply metric to level-2 links";
          }
        }
      }
    }
    container prc-interval {
      tailf:info
        "Minimum interval between partial route calculations";
      tailf:cli-compact-syntax;
      tailf:cli-sequence-commands;
      leaf interval {
        tailf:cli-drop-node-name;
        type uint32 {
          range "1 .. 120";
          tailf:info
            "<1-120>;;PRC interval in seconds";
        }
      }
      leaf initial-wait {
        tailf:cli-drop-node-name;
        type uint32 {
          range "1 .. 120000";
          tailf:info
            "<1-120000>;;Initial wait for PRC in milliseconds";
        }
      }
      leaf minimum-wait {
        tailf:cli-drop-node-name;
        type uint32 {
          range "1 .. 120000";
          tailf:info
            "<1-120000>;;Minimum wait between first and second PRC in milliseconds";
        }
      }
    }
    container set-overload-bit {
      tailf:info
        "Signal other routers not to use us in SPF";
      choice set-overload-bit-choice {
        container on-startup {
          tailf:info
            "Set overload-bit only temporarily after reboot";
          choice on-startup-choice {
            container time {
              tailf:cli-drop-node-name;
              tailf:cli-compact-syntax;
              tailf:cli-sequence-commands;
              leaf time {
                tailf:cli-drop-node-name;
                type uint32 {
                  range "5 .. 86400";
                  tailf:info
                    "<5-86400>;;Time in seconds to advertise ourself as overloaded after reboot";
                }
              }
              leaf suppress {
                tailf:info
                  "If overload-bit set, suppress the following types of IP prefixes";
                tailf:cli-incomplete-command;
                type empty;
              }
              uses set-overload-bit-suppress-grouping;
            }
            container wait-for-bgp {
              tailf:info
                "Let BGP decide when to unset the overload bit";
              presence "Let BGP decide when to unset the overload bitW";
              container suppress {
                tailf:info
                  "If overload-bit set, suppress the following types of IP prefixes";
                tailf:cli-compact-syntax;
                uses set-overload-bit-suppress-grouping;
              }
            }
          }
        }
        container suppress {
          tailf:info
            "If overload-bit set, suppress the following types of IP prefixes";
          tailf:cli-compact-syntax;
          uses set-overload-bit-suppress-grouping;
        }
      }
    }
    container spf-interval {
      tailf:info
        "Minimum interval between SPF calculations";
      tailf:cli-compact-syntax;
      choice spf-interval-choice {
        list level-1-2 {
          tailf:cli-drop-node-name;
          tailf:cli-suppress-mode;
          tailf:cli-delete-when-empty;
          tailf:cli-compact-syntax;
          tailf:cli-sequence-commands;
          tailf:cli-incomplete-command;
          key "level";
          leaf level {
            type enumeration {
              enum "level-1" {
                tailf:info
                  "Set interval for level 1 only";
              }
              enum "level-2" {
                tailf:info
                  "Set interval for level 2 only";
              }
            }
          }
          uses spf-intervals-grouping;
        }
        container intervals {
          tailf:cli-drop-node-name;
          tailf:cli-compact-syntax;
          tailf:cli-sequence-commands;
          uses spf-intervals-grouping;
        }
      }
    }
    container traffic-share {
      tailf:info
        "How to compute traffic share over alternate paths";
      container min {
        tailf:info
          "All traffic shared among min metric paths";
        leaf across-interface {
          tailf:info
            "Use different interfaces for equal-cost paths";
          type empty;
        }
      }
    }
  }

  grouping isis-main-grouping {
    container isis-main-container {
      tailf:cli-full-command;
      tailf:cli-drop-node-name;
      uses isis-address-family-grouping;
      container address-family {
        tailf:info
          "Enter Address Family command mode";
        container ipv6 {
          tailf:info
            "Address family";
          container unicast {
            tailf:cli-add-mode;
            tailf:cli-mode-name "config-router-af";
            tailf:info
              "Address Family Modifier";
            tailf:cli-full-command;
            tailf:cli-exit-command "exit-address-family" {
              tailf:info
                "Exit from Address Family configuration mode";
            }
            uses isis-address-family-grouping;
            leaf distance {
              tailf:info
                "Administrative distance";
              tailf:cli-full-command;
              type uint32 {
                range "1 .. 255";
                tailf:info
                  "<1-255>;;OSPF Administrative distance";
              }
            }
            container multi-topology {
              tailf:info
                "Enable multi-topology mode";
              presence "Enable multi-topology mode";
              leaf transition {
                tailf:info
                  "Accept and generate both IS-IS IPv6 and Multi-topology IPv6 TLVs";
                type empty;
              }
            }
            container redistribute {
              tailf:info
                "Redistribute IPv6 prefixes from another routing protocol";
              container bgp {
                tailf:info
                  "Border Gateway Protocol (BGP)";
                tailf:cli-sequence-commands;
                tailf:cli-compact-syntax;
                leaf as-number {
                  tailf:cli-drop-node-name;
                  type uint32 {
                    range "1 .. 65535";
                    tailf:info
                      "<1-65535>;;Autonomous system number";
                  }
                }
                uses isis-redist-af-grouping;
              }
              container connected {
                tailf:info
                  "Connected";
                presence "Connected";
                uses isis-redist-grouping;
              }
              list eigrp {
                tailf:info
                  "Enhanced Interior Gateway Routing Protocol (EIGRP)";
                tailf:cli-suppress-mode;
                tailf:cli-delete-when-empty;
                key "as-number";
                leaf as-number {
                  tailf:cli-drop-node-name;
                  type uint32 {
                    range "1 .. 65535";
                    tailf:info
                      "<1-65535>;;Autonomous system number";
                  }
                }
                uses isis-redist-af-grouping;
              }
              container isis {
                tailf:info
                  "ISO IS-IS";
                tailf:cli-compact-syntax;
                leaf area-tag {
                  tailf:cli-drop-node-name;
                  tailf:cli-disallow-value "level-1|level-2";
                  type string {
                    tailf:info
                      "WORD;;IPv6 process name";
                  }
                }
                container levels {
                  tailf:cli-drop-node-name;
                  tailf:cli-sequence-commands;
                  leaf isis-redist-levels1 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf into {
                    tailf:info
                      "from level-n into level-m";
                    tailf:cli-incomplete-command;
                    type empty;
                  }
                  leaf isis-redist-levels2 {
                    tailf:cli-drop-node-name;
                    tailf:cli-incomplete-command;
                    type enumeration {
                      enum "level-1" {
                        tailf:info
                          "Inter-area routes from level-1";
                      }
                      enum "level-2" {
                        tailf:info
                          "Inter-area routes from level-2";
                      }
                    }
                  }
                  leaf distribute-list {
                    tailf:info
                      "select routes";
                    type string {
                      tailf:info
                        "WORD;;IPv6 prefix-list name";
                    }
                  }
                }
              }
              container nemo {
                tailf:info
                  "Network Mobility (NEMO)";
                tailf:cli-compact-syntax;
                uses isis-redist-af-grouping;
              }
              list ospf {
                tailf:info
                  "Open Shortest Path First (OSPF)";
                tailf:cli-suppress-mode;
                tailf:cli-delete-when-empty;
                key "process-id";
                leaf process-id {
                  tailf:cli-suppress-range;
                  type uint32 {
                    range "1 .. 65535";
                    tailf:info
                      "<1-65535>;;Process ID";
                  }
                }
                uses isis-redist-af-grouping;
                container match {
                  tailf:cli-compact-syntax;
                  tailf:cli-flatten-container;
                  tailf:info
                    "Redistribution of OSPF routes";
                  container internal {
                    presence "Redistribute OSPF internal routes";
                    tailf:info
                      "Redistribute OSPF internal routes";
                    tailf:cli-compact-syntax;
                    tailf:cli-flatten-container;
                    uses isis-redist-ospf-match-grouping;
                  }
                  container external {
                    tailf:info
                      "Redistribute OSPF external routes";
                    presence "Redistribute OSPF external routes";
                    tailf:cli-compact-syntax;
                    tailf:cli-flatten-container;
                    leaf external-routes {
                      tailf:cli-drop-node-name;
                      type redist-ospf-external-type;
                    }
                    uses isis-redist-ospf-match-grouping;
                  }
                  container nssa-external {
                    tailf:info
                      "Redistribute OSPF NSSA external routes";
                    presence "Redistribute OSPF NSSA external routes";
                    tailf:cli-compact-syntax;
                    tailf:cli-flatten-container;
                    leaf nssa-external-routes {
                      tailf:cli-drop-node-name;
                      type redist-ospf-external-type;
                    }
                    uses isis-redist-ospf-match-grouping;
                  }
                }
              }
              list rip {
                tailf:info
                  "IPv6 Routing Information Protocol (RIPv6)";
                tailf:cli-suppress-mode;
                tailf:cli-delete-when-empty;
                key "process";
                leaf process {
                  type string {
                    tailf:info
                      "WORD;;User selected string identifying this process";
                  }
                }
                uses isis-redist-af-grouping;
              }
              container static {
                tailf:info
                  "Static routes";
                presence "Static routes";
                uses isis-redist-grouping;
              }
            }
            list summary-prefix {
              tailf:info
                "Configure IPv6 summary prefix";
              tailf:cli-suppress-mode;
              tailf:cli-delete-when-empty;
              key "prefix";
              leaf prefix {
                type inet:ipv6-prefix {
                  tailf:info
                    "X:X:X:X::X/<0-128>;;IPv6 prefix x:x::y/<z>";
                }
              }
              leaf levels {
                tailf:cli-drop-node-name;
                type enumeration {
                  enum "level-1" {
                    tailf:info
                      "Summarize into level-1 area";
                  }
                  enum "level-1-2" {
                    tailf:info
                      "Summarize into both area and sub-domain";
                  }
                  enum "level-2" {
                    tailf:info
                      "Summarize into level-2 sub-domain";
                  }
                }
              }
            }
          }
        }
      }
      container advertise {
        tailf:info
          "Control which IP routes flow in L1 and L2 LSPs";
        leaf passive-only {
          tailf:info
            "only interface address of passive interfaces";
          type empty;
        }
      }
      container area-password {
        tailf:info
          "Configure the authentication password for an area";
        tailf:cli-sequence-commands;
        tailf:cli-compact-syntax;
        leaf name {
          tailf:cli-drop-node-name;
          type string {
            tailf:info
              "WORD;;Area password";
          }
        }
        uses authenticate-snp-grouping;
      }
      container authentication {
        tailf:info
          "ISIS authentication for LSPs";
        container mode {
          tailf:info
            "Authentication mode";
          container md5 {
            tailf:info
              "Keyed message digest";
            presence "Keyed message digest";
            uses authentication-level-grouping;
          }
          container text {
            tailf:info
              "Clear text password";
            presence "Clear text password";
            uses authentication-level-grouping;
          }
        }
        container key-chain {
          tailf:info
            "Authentication key-chain";
          tailf:cli-compact-syntax;
          tailf:cli-sequence-commands;
          leaf name {
            tailf:cli-drop-node-name;
            type string {
              tailf:info
                "WORD;;Name of key-chain";
            }
          }
          uses authentication-level-grouping;
        }
        container send-only {
          tailf:info
            "Authentication send only, receive ignore";
          presence "Authentication send only, receive ignore";
          uses authentication-level-grouping;
        }
      }
      container bfd {
        tailf:info
          "BFD configuration commands";
        leaf all-interfaces {
          tailf:info
            "Enable BFD on all interfaces";
          type empty;
        }
      }
      container distance {
        tailf:info
          "Define an administrative distance";
        tailf:cli-compact-syntax;
        container clns-container {
          tailf:cli-drop-node-name;
          tailf:cli-sequence-commands;
          leaf distance {
            tailf:cli-drop-node-name;
            type uint32 {
              range "1 .. 255";
              tailf:info
                "<1-255>;;OSPF Administrative distance";
            }
          }
          leaf clns {
            tailf:info
              "Distance applied for CLNS derived routes";
            tailf:cli-full-command;
            type empty;
          }
        }
        container ip-container {
          tailf:cli-drop-node-name;
          tailf:cli-sequence-commands;
          leaf distance {
            tailf:cli-drop-node-name;
            type uint32 {
              range "1 .. 255";
              tailf:info
                "<1-255>;;OSPF Administrative distance";
            }
          }
          leaf ip {
            tailf:info
              "Distance applied for IP derived routes";
            tailf:cli-full-command;
            type empty;
          }
        }
        container acl-container {
          tailf:cli-drop-node-name;
          tailf:cli-sequence-commands;
          leaf distance {
            tailf:cli-drop-node-name;
            type uint32 {
              range "1 .. 255";
              tailf:info
                "<1-255>;;OSPF Administrative distance";
            }
          }
          list acl {
            tailf:cli-drop-node-name;
            tailf:cli-suppress-mode;
            tailf:cli-delete-when-empty;
            key "ip wildcard";
            leaf ip {
              type inet:ipv4-address {
                tailf:info
                  "A.B.C.D;;IP source address";
              }
            }
            leaf wildcard {
              type inet:ipv4-address {
                tailf:info
                  "A.B.C.D;;Wildcard bits";
              }
            }
            leaf acl-name {
              tailf:cli-drop-node-name;
              type access-list-standard-id-type;
              tailf:cli-no-value-on-delete;
            }
          }
        }
      }
      container domain-password {
        tailf:info
          "Set the authentication password for a routing domain";
        tailf:cli-sequence-commands;
        tailf:cli-compact-syntax;
        leaf name {
          tailf:cli-drop-node-name;
          type string {
            tailf:info
              "WORD;;Routing domain password";
          }
        }
        uses authenticate-snp-grouping;
      }
      container fast-flood {
        tailf:info
          "Flood LSPs (that triggered SPF) before running SPF";
        presence "Flood LSPs (that triggered SPF) before running SPF";
        leaf number {
          tailf:cli-drop-node-name;
          type uint32 {
            range "1 .. 15";
            tailf:info
              "<1-15>;;number of LSPs to be flooded before starting SPF";
          }
        }
      }
      container hello {
        tailf:info
          "Pad ISIS hello PDUs to full MTU";
        container padding {
          tailf:info
            "Pad hello PDU";
          presence "Pad hello PDU";
          leaf pad-type {
            tailf:cli-drop-node-name;
            type enumeration {
              enum "multi-point" {
                tailf:info
                  "Pad LAN hello PDUs";
              }
              enum "point-to-point" {
                tailf:info
                  "Pad point-to-point hello PDUs";
              }
            }
          }
        }
      }
      container hostname {
        tailf:info
          "Dynamic hostname for IS-IS";
        leaf dynamic {
          tailf:info
            "Dynamic hostname";
          type empty;
        }
      }
      leaf ignore-lsp-errors {
        tailf:info
          "Ignore LSPs with bad checksums";
        tailf:cli-full-command;
        type empty;
      }
      container ip {
        tailf:info
          "IP specific commands";
        container route {
          tailf:info
            "ISIS IP routes";
          container priority {
            tailf:info
              "Assign priority to IP prefixes";
            container high {
              tailf:info
                "Assign high priority to important IP prefixes in ISIS IP local RIB";
              leaf tag {
                tailf:info
                  "Assign high priority to IP prefixes with a specific route tag";
                type uint32 {
                  range "1 .. 4294967295";
                  tailf:info
                    "<1-4294967295>;;tag value";
                }
              }
            }
          }
        }
      }
      leaf is-type {
        tailf:info
          "IS Level for this routing process (OSI only)";
        tailf:cli-full-command;
        type enumeration {
          enum "level-1" {
            tailf:info
              "Act as a station router only";
          }
          enum "level-1-2" {
            tailf:info
              "Act as both a station router and an area router";
          }
          enum "level-2-only" {
            tailf:info
              "Act as an area router only";
          }
        }
      }
      container ispf {
        tailf:info
          "Configure execution of incremental SPF";
        tailf:cli-compact-syntax;
        tailf:cli-sequence-commands;
        leaf level {
          tailf:cli-drop-node-name;
          type enumeration {
            enum "level-1" {
              tailf:info
                "Do incremental SPF for level-1";
            }
            enum "level-1-2" {
              tailf:info
                "Do incremental SPF for both levels";
            }
            enum "level-2" {
              tailf:info
                "Do incremental SPF for level-2";
            }
          }
        }
        leaf number {
          tailf:cli-drop-node-name;
          type uint32 {
            range "1 .. 600";
            tailf:info
              "<1-600>;;Number of seconds before activating incremental-spf";
          }
        }
      }
      container log-adjacency-changes {
        tailf:info
          "Log changes in adjacency state";
        presence "Log changes in adjacency state";
        leaf all {
          tailf:info
            "Include changes generated by non-IIH event";
          type empty;
        }
      }
      container lsp-full {
        tailf:info
          "If we run out of LSP fragments";
        container suppress {
          tailf:info
            "suppress the following types of IP prefixes";
          choice lsp-full-choince {
            container external-interlevel-container {
              tailf:cli-drop-node-name;
              tailf:cli-compact-syntax;
              leaf external {
                tailf:info
                  "don't advertise IP prefixes learned from other protocols";
                type empty;
              }
              leaf interlevel {
                tailf:info
                  "don't advertise IP prefixes learned from another ISIS level";
                type empty;
              }
            }
            leaf none {
              tailf:info
                "don't suppress any prefixes";
              type empty;
            }
          }
        }
      }
      container lsp-gen-interval {
        tailf:info
          "Minimum interval between regenerating same LSP";
        choice lsp-gen-interval-choice {
          container intervals {
            tailf:cli-drop-node-name;
            tailf:cli-compact-syntax;
            tailf:cli-sequence-commands;
            uses lsp-gen-interval-grouping;
          }
          container intervals-levels {
            tailf:cli-drop-node-name;
            container intervals-level-1 {
              tailf:cli-drop-node-name;
              tailf:cli-compact-syntax;
              tailf:cli-sequence-commands;
              leaf level-1 {
                tailf:info
                  "Set interval for level 1 only";
                type empty;
              }
              uses lsp-gen-interval-grouping;
            }
            container intervals-level-2 {
              tailf:cli-drop-node-name;
              tailf:cli-compact-syntax;
              tailf:cli-sequence-commands;
              leaf level-2 {
                tailf:info
                  "Set interval for level 2 only";
                type empty;
              }
              uses lsp-gen-interval-grouping;
            }
          }
        }
      }
      leaf lsp-mtu {
        tailf:info
          "Set maximum LSP size";
        tailf:cli-full-command;
        type uint32 {
          range "128 .. 4352";
          tailf:info
            "<128-4352>;;Max LSP size in bytes";
        }
      }
      leaf lsp-refresh-interval {
        tailf:info
          "Set LSP refresh interval";
        tailf:cli-full-command;
        type uint32 {
          range "1 .. 65535";
          tailf:info
            "<1-65535>;;LSP refresh time in seconds";
        }
      }
      leaf max-area-addresses {
        tailf:info
          "Allow configuration of more manual area addresses";
        tailf:cli-full-command;
        type uint32 {
          range "3 .. 254";
          tailf:info
            "<3-254>;;Max number of manual area addresses";
        }
      }
      leaf max-lsp-lifetime {
        tailf:info
          "Set maximum LSP lifetime";
        tailf:cli-full-command;
        type uint32 {
          range "1 .. 65535";
          tailf:info
            "<1-65535>;;Maximum LSP lifetime in seconds";
        }
      }
      container metric-style {
        tailf:info
          "Use old-style (ISO 10589) or new-style packet formats";
        choice metric-style-choice {
          container narrow {
            tailf:info
              "Use old style of TLVs with narrow metric";
            presence "true";
            uses narrow-wide-transition-grouping;
          }
          container transition {
            tailf:info
              "Send and accept both styles of TLVs during transition";
            presence "true";
            leaf transition {
              type isis-level-type;
              tailf:cli-drop-node-name;
            }
          }
          container wide {
            tailf:info
              "Use new style of TLVs to carry wider metric";
            presence "true";
            uses narrow-wide-transition-grouping;
          }
        }
      }
      container mpls {
        tailf:info
          "Configure MPLS routing protocol parameters";
        container traffic-eng {
          tailf:info
            "routing protocol commands for MPLS Traffic Engineering";
          leaf level-1 {
            tailf:info
              "Run MPLS TE on IS-IS level 1 only";
            tailf:cli-full-command;
            type empty;
          }
          leaf level-2 {
            tailf:info
              "Run MPLS TE on IS-IS level 2 only";
            tailf:cli-full-command;
            type empty;
          }
          leaf multicast-intact {
            tailf:info
              "MPLS TE and PIM interaction";
            tailf:cli-full-command;
            type empty;
          }
          container router-id {
            tailf:info
              "Traffic Engineering stable IP address for system";
            tailf:cli-diff-dependency "/ios:interface" {
              tailf:xpath-root 3;
            }
            uses interface-grouping;
          }
          container scanner {
            tailf:info
              "Timer parameters for TE database";
            presence "Timer parameters for TE database";
            tailf:cli-compact-syntax;
            leaf interval {
              tailf:info
                "time (secs) between LSPDB walks for TE";
              type uint32 {
                range "1 .. 60";
                tailf:info
                  "<1-60>;;interval between LSPDB walks for TE TLVs extraction";
              }
            }
            leaf max-flash {
              tailf:info
                "Number of ISIS LSPs to be processed with no delay";
              type uint32 {
                range "0 .. 200";
                tailf:info
                  "<0-200>;;Max. number of LSPs ISIS may send to TE db without delay";
              }
            }
          }
        }
      }
      list net {
        tailf:info
          "A Network Entity Title for this process (OSI only)";
        tailf:cli-suppress-mode;
        tailf:cli-delete-when-empty;
        key "tag";
        leaf tag {
          type isis-net;
        }
      }
      container partition {
        tailf:info
          "CLNS area partition";
        leaf avoidance {
          tailf:info
            "Withdraw area prefix if partition detected";
          type empty;
        }
      }
      uses passive-interface-grouping;
      container protocol {
        tailf:info
          "Set protocol's administrative state";
        leaf shutdown {
          tailf:info
            "Set protocol's administrative state to disable";
          type empty;
        }
      }
      container redistribute {
        tailf:info
          "Redistribute information from another routing protocol";
        uses isis-redist-grouping;
        container bgp {
          tailf:info
            "Border Gateway Protocol (BGP)";
          tailf:cli-sequence-commands;
          tailf:cli-compact-syntax;
          leaf as-number {
            tailf:cli-drop-node-name;
            type uint32 {
              range "1 .. 65535";
              tailf:info
                "<1-65535>;;Autonomous system number";
            }
          }
          uses isis-redist-clns-ip-grouping;
        }
        container connected {
          tailf:info
            "Connected";
          presence "Connected";
          uses isis-redist-grouping;
        }
        list eigrp {
          tailf:info
            "Enhanced Interior Gateway Routing Protocol (EIGRP)";
          tailf:cli-suppress-mode;
          tailf:cli-delete-when-empty;
          key "as-number";
          leaf as-number {
            tailf:cli-drop-node-name;
            type uint32 {
              range "1 .. 65535";
              tailf:info
                "<1-65535>;;Autonomous system number";
            }
          }
          uses isis-redist-grouping;
        }
        container isis {
          tailf:info
            "ISO IS-IS";
          tailf:cli-compact-syntax;
          leaf area-tag {
            tailf:cli-full-command;
            tailf:cli-drop-node-name;
            tailf:cli-disallow-value "ip";
            type string {
              tailf:info
                "WORD;;ISO routing area tag";
            }
          }
          container ip {
            tailf:info
              "Redistribution of IP routes between levels";
            tailf:cli-compact-syntax;
            tailf:cli-sequence-commands;
            leaf isis-redist-levels1 {
              tailf:cli-drop-node-name;
              tailf:cli-incomplete-command;
              type enumeration {
                enum "level-1" {
                  tailf:info
                    "Inter-area routes from level-1";
                }
                enum "level-2" {
                  tailf:info
                    "Inter-area routes from level-2";
                }
              }
            }
            leaf into {
              tailf:info
                "from level-n into level-m";
              tailf:cli-incomplete-command;
              type empty;
            }
            leaf isis-redist-levels2 {
              tailf:cli-drop-node-name;
              tailf:cli-incomplete-command;
              type enumeration {
                enum "level-1" {
                  tailf:info
                    "Inter-area routes from level-1";
                }
                enum "level-2" {
                  tailf:info
                    "Inter-area routes from level-2";
                }
              }
            }
            choice isis-redist-isis-ip-choice {
              leaf distribute-list {
                tailf:info
                  "select routes";
                type uint32 {
                  range "100 .. 199";
                  tailf:info
                    "<100-199>;;IP extended acces-list number";
                }
              }
              leaf route-map {
                tailf:info
                  "Route map for route matching";
                type string {
                  tailf:info
                    "WORD;;Name of the route-map";
                }
              }
            }
          }
        }
        container iso-igrp {
          tailf:info
            "IGRP for OSI networks";
          presence "IGRP for OSI networks";
          tailf:cli-sequence-commands;
          choice iso-igrp-choice {
            container area-tag-route-map-container {
              tailf:cli-drop-node-name;
              tailf:cli-sequence-commands;
              tailf:cli-flatten-container;
              leaf area-tag {
                tailf:cli-drop-node-name;
                tailf:cli-disallow-value "route-map";
                type string {
                  tailf:info
                    "WORD;;ISO routing area tag";
                }
              }
              leaf route-map {
                tailf:info
                  "Route map reference";
                type string {
                  tailf:info
                    "WORD;;Pointer to route-map entries";
                }
              }
            }
            leaf route-map {
              tailf:info
                "Route map reference";
              type string {
                tailf:info
                  "WORD;;Pointer to route-map entries";
              }
            }
          }
          uses redist-level-grouping;
          leaf metric {
            tailf:info
              "ISIS default metric";
            type uint32 {
              range "0 .. 4294967295";
              tailf:info
                "<0-4294967295>;;ISIS default metric";
            }
          }
          leaf metric-type {
            tailf:info
              "OSPF/IS-IS exterior metric type for redistributed routes";
            type enumeration {
              enum "external" {
                tailf:info
                  "Set IS-IS External metric type";
              }
              enum "internal" {
                tailf:info
                  "Set IS-IS Internal metric type";
              }
            }
          }
        }
        container maximum-prefix {
          tailf:info
            "Maximum number of prefixes redistributed to protocol";
          tailf:cli-compact-syntax;
          tailf:cli-sequence-commands;
          leaf number {
            tailf:cli-drop-node-name;
            type uint32 {
              range "1 .. 4294967295";
              tailf:info
                "<1-4294967295>;;Maximum number of IP prefixes redistributed";
            }
          }
          leaf threshold-value {
            tailf:cli-drop-node-name;
            tailf:cli-break-sequence-commands;
            type uint32 {
              range "1 .. 100";
              tailf:info
                "<1-100>;;Threshold value (%) at which to generate a warning message";
            }
          }
          leaf warning-only {
            tailf:info
              "Only give warning message when limit is exceeded";
            tailf:cli-full-command;
            type empty;
          }
          leaf withdraw {
            tailf:info
              "Withdraw redistibuted prefixes";
            tailf:cli-full-command;
            type empty;
          }
        }
        container mobile {
          tailf:info
            "Mobile routes";
          presence "Mobile routes";
          uses isis-redist-grouping;
        }
        container odr {
          tailf:info
            "On Demand stub Routes";
          presence "On Demand stub Routes";
          uses isis-redist-grouping;
        }
        list ospf {
          tailf:info
            "Open Shortest Path First (OSPF)";
          tailf:cli-suppress-mode;
          tailf:cli-delete-when-empty;
          key "process-id";
          leaf process-id {
            tailf:cli-suppress-range;
            type uint32 {
              range "1 .. 65535";
              tailf:info
                "<1-65535>;;Process ID";
            }
          }
          uses isis-redist-grouping;
          container match {
            tailf:cli-compact-syntax;
            tailf:cli-flatten-container;
            tailf:info
              "Redistribution of OSPF routes";
            container internal {
              presence "Redistribute OSPF internal routes";
              tailf:info
                "Redistribute OSPF internal routes";
              tailf:cli-compact-syntax;
              tailf:cli-flatten-container;
              uses isis-redist-ospf-match-grouping;
            }
            container external {
              tailf:info
                "Redistribute OSPF external routes";
              presence "Redistribute OSPF external routes";
              tailf:cli-compact-syntax;
              tailf:cli-flatten-container;
              leaf external-routes {
                tailf:cli-drop-node-name;
                type redist-ospf-external-type;
              }
              uses isis-redist-ospf-match-grouping;
            }
            container nssa-external {
              tailf:info
                "Redistribute OSPF NSSA external routes";
              presence "Redistribute OSPF NSSA external routes";
              tailf:cli-compact-syntax;
              tailf:cli-flatten-container;
              leaf nssa-external-routes {
                tailf:cli-drop-node-name;
                type redist-ospf-external-type;
              }
              uses isis-redist-ospf-match-grouping;
            }
          }
          leaf vrf {
            tailf:info
              "VPN Routing/Forwarding Instance";
            tailf:cli-diff-dependency "/ios:ip/vrf" {
              tailf:xpath-root 3;
            }
            tailf:cli-diff-dependency "/ios:vrf/definition" {
              tailf:xpath-root 3;
            }
            type string {
              tailf:info
                "WORD;;VPN Routing/Forwarding Instance (VRF) name";
            }
          }
        }
        container rip {
          tailf:info
            "Routing Information Protocol (RIP)";
          presence "Routing Information Protocol (RIP)";
          uses isis-redist-grouping;
        }
        container static {
          tailf:info
            "Static routes";
          presence "Static routes";
          uses isis-redist-clns-ip-grouping;
        }
      }
      container set-attached-bit {
        tailf:info
          "Conditionally advertise us as attached to L2";
        leaf route-map {
          tailf:info
            "Route-map reference";
          type string {
            tailf:info
              "WORD;;Route map name";
          }
        }
      }
      list summary-address {
        tailf:info
          "Configure IP address summaries";
        tailf:cli-suppress-mode;
        tailf:cli-delete-when-empty;
        key "ip mask";
        leaf ip {
          type inet:ipv4-address {
            tailf:info
              "A.B.C.D;;IP summary address";
          }
        }
        leaf mask {
          type inet:ipv4-address {
            tailf:info
              "A.B.C.D;;Summary mask";
          }
        }
        container level-1 {
          tailf:info
            "Summarize into level-1 area";
          presence "Summarize into level-1 area";
          tailf:cli-compact-syntax;
          uses summary-address-metric-tag-grouping;
        }
        container level-1-2 {
          tailf:info
            "Summarize into both area and sub-domain";
          presence "Summarize into both area and sub-domain";
          tailf:cli-compact-syntax;
          uses summary-address-metric-tag-grouping;
        }
        container level-2 {
          tailf:info
            "Summarize into level-2 sub-domain";
          presence "Summarize into level-2 sub-domain";
          tailf:cli-compact-syntax;
          uses summary-address-metric-tag-grouping;
        }
        container metric-tag-container {
          tailf:cli-drop-node-name;
          tailf:cli-compact-syntax;
          uses summary-address-metric-tag-grouping;
        }
      }
      leaf update-queue-depth {
        tailf:info
          "Set Update process queue depth";
        type uint32 {
          range "1 .. 2147483647";
          tailf:info
            "<1-2147483647>;;Max queue depth";
        }
      }
      container use {
        tailf:info
          "Use different algorithms during SPF";
        leaf external-metrics {
          tailf:info
            "Honour external metrics during SPF";
          type empty;
        }
      }
    }
  }

  grouping interface-switch-grouping {
    container switchport-conf {
      tailf:cli-no-keyword;
      tailf:cli-drop-node-name;
      leaf switchport {
        tailf:cli-boolean-no;
        type boolean;
      }
    }
    container switchport {
      tailf:info
        "Set switching mode characteristics";
      tailf:cli-incomplete-no;
      container access {
        tailf:info
          "Set access mode characteristics of the interface";
        leaf vlan {
          tailf:info
            "Set VLAN when interface is in access mode";
          tailf:cli-diff-dependency "/ios:vlan/vlan-list/id" {
            tailf:xpath-root 3;
          }
          type union {
            type uint16 {
              tailf:info
                "<1-4094>;;VLAN ID of the VLAN when this port is in access mode";
              range "1..4094";
            }
            type enumeration {
              enum "dynamic" {
                tailf:info
                  "When in access mode, this interfaces VLAN is controlled by VMPS";
              }
            }
          }
        }
      }
      container block {
        tailf:info
          "Disable forwarding of unknown uni/multi cast addresses";
        leaf multicast {
          tailf:info
            "Block unknown multicast addresses";
          tailf:cli-full-command;
          type empty;
        }
        leaf unicast {
          tailf:cli-full-command;
          tailf:info
            "Block unknown unicast addresses";
          type empty;
        }
      }
      container mode {
        tailf:info
          "Set trunking mode of the interface";
        choice mode-choice {
          container access {
            presence "true";
            tailf:info
              "Set trunking mode to ACCESS unconditionally";
          }
          container dot1q-tunnel {
            presence "true";
            tailf:info
              "set trunking mode to TUNNEL unconditionally";
          }
          leaf dynamic {
            tailf:info
              "Set trunking mode to dynamically negotiate access or trunk mode";
            type enumeration {
              enum "auto" {
                tailf:info
                  "Set trunking mode dynamic negotiation parameter to AUTO";
              }
              enum "desirable" {
                tailf:info
                  "Set trunking mode dynamic negotiation parameter to DESIRABLE";
              }
            }
          }
          container trunk {
            presence "true";
            tailf:info
              "Set trunking mode to TRUNK unconditionally";
          }
        }
      }
      leaf nonegotiate {
        tailf:info
          "Device will not engage in negotiation protocol on this interface";
        type empty;
      }
      container port-security {
        tailf:info
          "Security related command";
        presence "true";
        container aging {
          tailf:info
            "Port-security aging commands";
          leaf time {
            tailf:info
              "Port-security aging time";
            type uint16 {
              tailf:info
                "<1-1440>;;Aging time in minutes. Enter a value between 1 and 1440";
              range "1..1440";
            }
          }
          leaf type {
            tailf:info
              "Port-security aging type";
            type enumeration {
              enum "absolute" {
                tailf:info
                  "Absolute aging (default)";
              }
              enum "inactivity" {
                tailf:info
                  "Aging based on inactivity time period";
              }
            }
          }
        }
        container mac-address {
          tailf:info
            "Secure mac address";
          tailf:cli-sequence-commands {
            tailf:cli-reset-siblings;
          }
          tailf:cli-compact-syntax;
          leaf sticky {
            tailf:info
              "Configure dynamic secure addresses as sticky";
            tailf:cli-optional-in-sequence;
            type empty;
          }
          leaf hw-address {
            tailf:cli-drop-node-name;
            type yang:mac-address {
              tailf:info
                "H.H.H;;48 bit mac address";
            }
          }
          leaf vlan {
            tailf:info
              "set VLAN ID of the VLAN on which this address can be learned";
            type uint16 {
              tailf:info
                "<1-4094>;;VLAN ID on which this address can be learned";
              range "1..4094";
            }
          }
        }
        container maximum {
          tailf:info
            "Max secure addresses";
          tailf:cli-sequence-commands {
            tailf:cli-reset-siblings;
          }
          tailf:cli-compact-syntax;
          leaf max-addresses {
            tailf:cli-drop-node-name;
            type uint16 {
              tailf:info
                "<1-4097>;;Maximum addresses";
              range "1..4097";
            }
          }
          leaf vlan {
            tailf:info
              "Max secure addresses per vlan";
            type string {
              tailf:info
                "WORD;;VLAN IDs to which this maximum applies";
            }
          }
        }
        leaf violation {
          tailf:info
            "Security violation mode";
          type enumeration {
            enum "protect" {
              tailf:info
                "Security violation protect mode";
            }
            enum "restrict" {
              tailf:info
                "Security violation restrict mode";
            }
            enum "shutdown" {
              tailf:info
                "Security violation shutdown mode";
            }
          }
        }
      }
      container trunk {
        tailf:info
          "Set trunking characteristics of the interface";
        container allowed {
          tailf:info
            "Set allowed VLAN characteristics when interface is in trunking mode";
          container vlan {
            tailf:info
              "Set allowed VLANs when interface is in trunking mode";
            choice vlan-choice {
              leaf-list vlans {
                tailf:cli-replace-all;
                tailf:cli-range-list-syntax;
                tailf:cli-drop-node-name;
                type uint16 {
                  tailf:info
                    "WORD;;VLAN IDs of the allowed VLANs when this port is in trunking mode";
                }
              }
              leaf all {
                tailf:info
                  "all VLANs";
                type empty;
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
        leaf encapsulation {
          tailf:info
            "Set encapsulation format on trunk port";
          type enumeration {
            enum "dot1q";
            enum "isl";
            enum "negotiate";
          }
        }
        container native {
          tailf:info
            "Set trunking native characteristics when interface is in trunking mode";
          leaf vlan {
            tailf:info
              "Set native VLAN when interface is in trunking mode";
            type union {
              type enumeration {
                enum "tag" {
                  tailf:info
                    "Set native VLAN tagging state";
                }
              }
              type uint16 {
                tailf:info
                  "<1-4094>;;VLAN ID of the native VLAN when this port is in trunking mode";
                range "1..4094";
              }
            }
          }
        }
        container pruning {
          tailf:info
            "Set pruning VLAN characteristics when interface is in trunking mode";
          container vlan {
            tailf:info
              "Set VLANs enabled for pruning when interface is in trunking mode";
            choice vlan-choice {
              leaf-list vlans {
                tailf:cli-range-list-syntax;
                tailf:cli-drop-node-name;
                type uint16 {
                  tailf:info
                    "WORD;;VLAN IDs of the allowed VLANs when this port is in trunking mode";
                }
              }
              leaf-list except {
                tailf:info
                  "all VLANs except the following";
                tailf:cli-range-list-syntax;
                type uint16 {
                  tailf:info
                    "WORD;;VLAN IDs of the allowed VLANs when this port is in trunking mode";
                }
              }
              leaf none {
                tailf:info
                  "no VLANs";
                type empty;
              }
            }
          }
        }
      }
      container voice {
        tailf:info
          "Voice appliance attributes";
        leaf vlan {
          tailf:info
            "Vlan for voice traffic";
          type union {
            type enumeration {
              enum "dot1p" {
                tailf:info
                  "Priority tagged on PVID";
              }
              enum "none" {
                tailf:info
                  "Don't tell telephone about voice vlan";
              }
              enum "untagged" {
                tailf:info
                  "Untagged on PVID";
              }
            }
            type uint16 {
              tailf:info
                "<1-4094>;;Vlan for voice traffic";
              range "1..4094";
            }
          }
        }
        container detect {
          tailf:info
            "detection enhancement keyword";
          tailf:cli-incomplete-command;
          container cisco-phone {
            tailf:info
              "Cisco IP phone";
            presence "true";
            leaf full-duplex {
              tailf:info
                "full duplex keyword";
              type empty;
            }
          }
        }
      }
      container priority {
        tailf:info
          "Set appliance 802.1p priority";
        tailf:cli-incomplete-command;
        container extend {
          tailf:info
            "Set appliance 802.1p priority";
          tailf:cli-incomplete-command;
          choice trust-choice {
            leaf trust {
              tailf:cli-full-command;
              tailf:info
                "Trust 802.1p priorities of devices on appliance";
              type empty;
            }
            leaf cos {
              tailf:info
                "Override 802.1p priority of devices on appliance";
              tailf:cli-full-command;
              type uint8 {
                tailf:info
                  "<0-7>;;Priority for devices on appliance";
                range "0..7";
              }
            }
          }
        }
      }
      container autostate {
        tailf:info
          "Include or exclude this port from vlan link up calculation";
        tailf:cli-incomplete-command;
        leaf exclude {
          tailf:info
            "Exclude this port from vlan link up calculation";
          type empty;
        }
      }
      leaf protected {
        tailf:info
          "Configure an interface to be a protected port";
        type empty;
      }
      leaf host {
        tailf:info
          "Set port host";
        type empty;
      }
    }
    container spanning-tree {
      tailf:info
        "Spanning Tree Subsystem";
      leaf bpdufilter {
        tailf:info
          "Don't send or receive BPDUs on this interface";
        type enumeration {
          enum "disable" {
            tailf:info
              "Disable BPDU filtering for this interface";
          }
          enum "enable" {
            tailf:info
              "Enable BPDU filtering for this interface";
          }
        }
      }
      container bpduguard {
        tailf:info
          "Don't accept BPDUs on this interface";
        choice bpduguard-choice {
          leaf disable {
            tailf:info
              "Disable BPDU guard for this interface";
            type empty;
          }
          leaf enable {
            type empty;
            tailf:info
              "Enable BPDU guard for this interface";
          }
        }
      }
      leaf cost {
        tailf:info
          "To set the path cost of the interface";
        tailf:cli-full-command;
        type uint32 {
          range "1..200000000";
        }
      }
      leaf guard {
        tailf:info
          "Change an interface's spanning tree guard mode";
        tailf:cli-full-command;
        type enumeration {
          enum "loop" {
            tailf:info
              "Set guard mode to loop guard on interface";
          }
          enum "none" {
            tailf:info
              "Set guard mode to none";
          }
          enum "root" {
            tailf:info
              "Set guard mode to root guard on interface";
          }
        }
      }
      leaf link-type {
        tailf:info
          "Specify a link type for spanning tree tree protocol use";
        tailf:cli-full-command;
        type enumeration {
          enum "auto" {
            tailf:code-name "link_type_auto";
            tailf:info
              "Determine link type based on media duplex of this interface";
          }
          enum "none" {
            tailf:info
              "Consider the interface as point-to-point";
          }
          enum "point-to-point" {
            tailf:info
              "Consider the interface as point-to-point";
          }
          enum "root" {
            tailf:info
              "Consider the interface as shared";
          }
        }
      }
      container portfast {
        tailf:info
          "Spanning tree portfast options";
        tailf:cli-delete-when-empty;
        presence "true";
        leaf enable {
          tailf:cli-full-command;
          tailf:cli-drop-node-name;
          type enumeration {
            enum "disable" {
              tailf:info
                "Disable portfast for this interface";
            }
          }
        }
        leaf trunk {
          type empty;
        }
      }
      container loopguard {
        tailf:info
          "Spanning tree loopguard options";
        leaf default {
          tailf:info
            "Enable loopguard by default on all ports";
          type empty;
        }
      }
    }
    container srr-queue {
      container bandwidth {
        container shape {
          tailf:cli-compact-syntax;
          tailf:cli-sequence-commands;
          tailf:cli-reset-container;
          leaf weight1 {
            tailf:cli-drop-node-name;
            tailf:cli-incomplete-command;
            type uint16;
          }
          leaf weight2 {
            tailf:cli-drop-node-name;
            tailf:cli-incomplete-command;
            type uint16;
          }
          leaf weight3 {
            tailf:cli-drop-node-name;
            tailf:cli-incomplete-command;
            type uint16;
          }
          leaf weight4 {
            tailf:cli-drop-node-name;
            type uint16;
          }
        }
        container share {
          tailf:cli-compact-syntax;
          tailf:cli-sequence-commands;
          tailf:cli-reset-container;
          leaf weight1 {
            tailf:cli-drop-node-name;
            tailf:cli-incomplete-command;
            type uint8 {
              range "1..255";
            }
          }
          leaf weight2 {
            tailf:cli-drop-node-name;
            tailf:cli-incomplete-command;
            type uint8 {
              range "1..255";
            }
          }
          leaf weight3 {
            tailf:cli-drop-node-name;
            tailf:cli-incomplete-command;
            type uint8 {
              range "1..255";
            }
          }
          leaf weight4 {
            tailf:cli-drop-node-name;
            type uint8 {
              range "1..255";
            }
          }
        }
      }
    }
  }

  grouping password-07-grouping {
    leaf level {
      tailf:info
        "Set exec level password";
      tailf:cli-optional-in-sequence;
      type uint8 {
        tailf:info
          "<1-15>;;Level number";
      }
    }
    leaf type {
      tailf:cli-drop-node-name;
      tailf:cli-optional-in-sequence;
      type enumeration {
        enum "0" {
          tailf:info
            "Specifies an UNENCRYPTED password will follow";
        }
        enum "7" {
          tailf:info
            "Specifies a HIDDEN password will follow";
        }
      }
    }
    leaf secret {
      tailf:cli-drop-node-name;
      type string {
        tailf:info
          "LINE;;The UNENCRYPTED (cleartext) password";
      }
    }
  }

  grouping aaa-authentication-dot1x-grouping {
    leaf group {
      tailf:info
        "Use Server-group";
      type union {
        type string {
          tailf:info
            "Server-group name";
        }
        type enumeration {
          enum "radius" {
            tailf:info
              "Use list of all Radius hosts.";
          }
          enum "tacacs+" {
            tailf:info
              "Use list of all Tacacs+ hosts.";
          }
        }
      }
    }
  }

  augment "/ncs:devices/ncs:device/ncs:config" {
    leaf version {
      tailf:ncs-device-type "cli-ned";
      tailf:display-when "not(../../ncs:module) or ../../ncs:module[ncs:name='tailf-ned-cisco-ios']";
      tailf:info
        "Version";
      type string {
        tailf:info
          "WORD;;Version number";
      }
    }
    container service {
      tailf:ncs-device-type "cli-ned";
      tailf:display-when "not(../../ncs:module) or ../../ncs:module[ncs:name='tailf-ned-cisco-ios']";
      tailf:info
        "Modify use of network based services";
      container pad {
        tailf:info
          "Enable PAD commands";
        tailf:cli-show-no;
        presence "true";
        leaf cmns {
          tailf:info
            "Enable PAD over CMNS connections";
          type empty;
        }
        leaf from-xot {
          tailf:info
            "Accept XOT to PAD connections";
          type empty;
        }
        leaf to-xot {
          tailf:info
            "Allow outgoing PAD over XOT connections";
          type empty;
        }
      }
      leaf password-encryption {
        tailf:info
          "Encrypt system passwords";
        tailf:cli-full-command;
        type empty;
      }
      container timestamps {
        tailf:info
          "Timestamp debug/log messages";
        tailf:cli-compact-syntax;
        tailf:cli-delete-when-empty;
        presence "true";
        container debug {
          tailf:info
            "Timestamp debug messages";
          container datetime {
            tailf:info
              "Timestamp with date and time";
            tailf:cli-compact-syntax;
            tailf:cli-delete-when-empty;
            presence "true";
            leaf localtime {
              tailf:info
                "Use local time zone for timestamps";
              type empty;
            }
            leaf msec {
              tailf:info
                "Include milliseconds in timestamp";
              type empty;
            }
            leaf show-timezone {
              tailf:info
                "Add time zone information to timestamp";
              type empty;
            }
            leaf year {
              tailf:info
                "Include year in timestamp";
              type empty;
            }
          }
          leaf uptime {
            tailf:info
              "Timestamp with system uptime";
            type empty;
          }
        }
        container log {
          tailf:info
            "Timestamp log messages";
          container datetime {
            tailf:info
              "Timestamp with date and time";
            tailf:cli-compact-syntax;
            tailf:cli-delete-when-empty;
            presence "true";
            leaf localtime {
              tailf:info
                "Use local time zone for timestamps";
              type empty;
            }
            leaf msec {
              tailf:info
                "Include milliseconds in timestamp";
              type empty;
            }
            leaf show-timezone {
              tailf:info
                "Add time zone information to timestamp";
              type empty;
            }
            leaf year {
              tailf:info
                "Include year in timestamp";
              type empty;
            }
          }
          leaf uptime {
            tailf:info
              "Timestamp with system uptime";
            type empty;
          }
        }
      }
      container alignment {
        tailf:info
          "Control alignment correction and logging";
        leaf detection {
          tailf:info
            "Enable detection of alignment issues";
          type empty;
        }
        leaf logging {
          tailf:info
            "Enable logging of alignment issues";
          type empty;
        }
      }
      leaf call-home {
        tailf:info
          "Enable call-home service";
        tailf:cli-full-command;
        type empty;
      }
      leaf compress-config {
        tailf:info
          "Compress the configuration file";
        tailf:cli-full-command;
        type empty;
      }
      leaf config {
        tailf:info
          "TFTP load config files";
        tailf:cli-full-command;
        type empty;
      }
      container counters {
        tailf:info
          "Control aging of interface counters";
        container max {
          tailf:info
            "Maximum counter aging threshold";
          leaf age {
            tailf:info
              "Aging threshold";
            type uint8 {
              tailf:info
                "<0-60>;;Aging threshold value in seconds";
              range "0..60";
            }
          }
        }
      }
      leaf dhcp {
        tailf:info
          "Enable DHCP server and relay agent";
        tailf:cli-full-command;
        type empty;
      }
      leaf disable-ip-fast-frag {
        tailf:info
          "Disable IP particle-based fast fragmentation";
        tailf:cli-full-command;
        type empty;
      }
      leaf exec-callback {
        tailf:info
          "Enable exec callback";
        tailf:cli-full-command;
        type empty;
      }
      leaf exec-wait {
        tailf:info
          "Delay EXEC startup on noisy lines";
        tailf:cli-full-command;
        type empty;
      }
      leaf finger {
        tailf:info
          "Allow responses to finger requests";
        tailf:cli-full-command;
        type empty;
      }
      container heartbeat {
        tailf:info
          "Enable heartbeat processing";
        leaf fatal-count {
          tailf:info
            "Set heartbeat fatal count";
          type uint8 {
            tailf:info
              "<1-60>;;Number of timeouts until fatal error occurs";
            range "1..60";
          }
        }
        leaf interrupt-interval {
          tailf:info
            "Set heartbeat interrupt test interval";
          type uint8 {
            tailf:info
              "<0-60>;;Interval between interrupt level tests";
            range "0..60";
          }
        }
        leaf interrupt-max {
          tailf:info
            "Set maximum message count from interrupt test";
          type uint8 {
            tailf:info
              "<0-60>;;Maximum number of messages from interrupt test";
            range "0..60";
          }
        }
        leaf transmit-interval {
          tailf:info
            "Set heartbeat transmit interval";
          type uint8 {
            tailf:info
              "<1-30>;;Interval between heartbeat transmissions";
            range "1..30";
          }
        }
        leaf warning-timeout {
          tailf:info
            "Set heartbeat warning timeout interval";
          type uint8 {
            tailf:info
              "<5-60>;;Interval between heartbeat timeout warnings";
            range "5..60";
          }
        }
      }
      leaf hide-telnet-addresses {
        tailf:info
          "Hide destination addresses in telnet command";
        tailf:cli-full-command;
        type empty;
      }
      leaf linenumber {
        tailf:info
          "enable line number banner for each exec";
        tailf:cli-full-command;
        type empty;
      }
      leaf nagle {
        tailf:info
          "Enable Nagle's congestion control algorithm";
        tailf:cli-full-command;
        type empty;
      }
      leaf old-slip-prompts {
        tailf:info
          "Allow old scripts to operate with slip/ppp";
        tailf:cli-full-command;
        type empty;
      }
      leaf pt-vty-logging {
        tailf:info
          "Log significant VTY-Async events";
        tailf:cli-full-command;
        type empty;
      }
      leaf sequence-numbers {
        tailf:info
          "Stamp logger messages with a sequence number";
        tailf:cli-full-command;
        type empty;
      }
      leaf slave-log {
        tailf:info
          "Enable log capability of slave IPs";
        tailf:cli-full-command;
        type empty;
      }
      leaf tcp-keepalives-in {
        tailf:info
          "Generate keepalives on idle incoming network connections";
        tailf:cli-full-command;
        type empty;
      }
      leaf tcp-keepalives-out {
        tailf:info
          "Generate keepalives on idle outgoing network connections";
        tailf:cli-full-command;
        type empty;
      }
      leaf unsupported-transceiver {
        tailf:info
          "";
        tailf:cli-full-command;
        type empty;
      }
    }
    container platform {
      tailf:ncs-device-type "cli-ned";
      tailf:display-when "not(../../ncs:module) or ../../ncs:module[ncs:name='tailf-ned-cisco-ios']";
      tailf:info
        "platform specific configuration";
      leaf atm-cdvt {
        tailf:info
          "Configure platform atm cdvt";
        tailf:cli-boolean-no;
        type boolean;
      }
      container bfd {
        tailf:info
          "Platform specific BFD commands";
        leaf disable-offload {
          tailf:info
            "Disable bfd hw offload";
          type empty;
        }
        leaf allow-svi {
          tailf:cli-full-command;
          type empty;
        }
        leaf enable-offload {
          tailf:cli-full-command;
          type empty;
        }
      }
      container console {
        tailf:info
          "Direct IOS output to console";
        presence "true";
        leaf output {
          tailf:cli-drop-node-name;
          type enumeration {
            enum "serial" {
              tailf:info
                "Direct IOS output to serial port";
            }
            enum "virtual" {
              tailf:info
                "Direct IOS output to virtual console";
            }
          }
        }
      }
      container hardware {
        tailf:info
          "Configure platform hardware";
        container throughput {
          tailf:info
            "Configure throughput";
          choice throughput-choice {
            leaf disable {
              tailf:info
                "Disable throughput upgrade licenses";
              type enumeration {
                enum "internal-license" {
                  tailf:info
                    "Disable throughput internal license";
                }
              }
            }
            container level {
              tailf:info
                "Configure the current traffic throughput level";
              tailf:cli-compact-syntax;
              tailf:cli-sequence-commands;
              leaf kbps {
                tailf:cli-drop-node-name;
                type enumeration {
                  enum "10000" {
                    tailf:info
                      "throughput in kbps";
                  }
                  enum "25000" {
                    tailf:info
                      "throughput in kbps";
                  }
                  enum "50000" {
                    tailf:info
                      "throughput in kbps";
                  }
                }
              }
              leaf eval-only {
                tailf:info
                  "Use only evaluation license";
                type empty;
              }
            }
          }
        }
      }
      container ipsec {
        tailf:info
          "Platform specific ipsec command";
        leaf fips-mode {
          tailf:info
            "enable FIPS mode";
          type empty;
        }
        leaf gdoi {
          tailf:info
            "gdoi";
          type enumeration {
            enum "accept-both" {
              tailf:info
                "7200 like behaviour";
            }
          }
        }
        container llq {
          tailf:info
            "config LLQ";
          leaf qos-group {
            tailf:info
              "config LLQ QoS Group";
            type uint8 {
              tailf:info
                "<1-99>;;QoS group";
              range "1..99";
            }
          }
        }
        container reassemble {
          tailf:info
            "reassemble packets";
          leaf transit {
            tailf:info
              "transit IPSEC packets";
            type empty;
          }
        }
      }
      container multicast {
        tailf:info
          "Configure multicast";
        container mgre {
          tailf:info
            "Multi-point GRE tunnel";
          leaf injection {
            tailf:info
              "Enable packet injection";
            type empty;
          }
        }
        container oce {
          tailf:info
            "multicast oce";
          container flag {
            tailf:info
              "multicast oce flag";
            leaf suppress {
              tailf:info
                "Enable oce flag suppress";
              type empty;
            }
          }
        }
      }
      container punt-keepalive {
        tailf:info
          "punt-keepalive messages";
        leaf disable-kernel-core {
          tailf:info
            "Disable IOSXE kernel core generation for keepalive fault";
          type boolean;
          tailf:cli-boolean-no;
        }
        container settings {
          tailf:info
            "Set the keepalive parameters";
          leaf fatal-count {
            tailf:info
              "Set punt-inject keepalive fatal count";
            type uint16 {
              tailf:info
                "<15-60>;;Number of timeouts until fatal error occurs";
              range "15..60";
            }
          }
          leaf transmit-interval {
            tailf:info
              "Set punt-inject keepalive transmit interval";
            type uint16 {
              tailf:info
                "<2-30>;;Interval between punt/inject keepalive transmissions";
              range "2..30";
            }
          }
          leaf warning-count {
            tailf:info
              "Set punt-inject keepalive warning count";
            type uint16 {
              tailf:info
                "<10-60>;;Interval between punt/inject keepalive timeout warnings";
              range "10..60";
            }
          }
        }
      }
      container punt-policer {
        tailf:info
          "Configures punt policers";
        tailf:cli-compact-syntax;
        tailf:cli-sequence-commands {
          tailf:cli-reset-siblings;
        }
        leaf cause {
          tailf:cli-drop-node-name;
          type uint8 {
            tailf:info
              "<1-89>;;Punt cause to be policed";
            range "1..89";
          }
        }
        leaf max-rate {
          tailf:cli-drop-node-name;
          type uint16 {
            tailf:info
              "<10-32000>;;max punt rate for cause MPLS ICMP Can't Frag";
            range "10..32000";
          }
        }
        leaf high {
          tailf:info
            "High priority traffic only";
          type empty;
        }
      }
      container qos {
        tailf:info
          "Platform specific qos configuration";
        leaf marker-statistics {
          tailf:info
            "Configure marking statistics";
          type empty;
        }
        container match-statistics {
          tailf:info
            "Configure match stats";
          leaf per-filter {
            tailf:info
              "Configure per-filter match statistics";
            type empty;
          }
        }
        leaf performance-monitor {
          tailf:info
            "Configure performance-monitor statistics";
          type empty;
        }
      }
      container reload {
        tailf:info
          "Platform specific reload command";
        leaf immediate {
          tailf:info
            "Immediately stop forwarding traffic";
          type empty;
        }
      }
      leaf shell {
        tailf:info
          "Control platform shell access command availability";
        type boolean;
        tailf:cli-boolean-no;
      }
    }
    leaf hostname {
      tailf:ncs-device-type "cli-ned";
      tailf:display-when "not(../../ncs:module) or ../../ncs:module[ncs:name='tailf-ned-cisco-ios']";
      tailf:info
        "Set system's network name";
      type string {
        tailf:info
          "This system's network name";
      }
    }
    container enable {
      tailf:ncs-device-type "cli-ned";
      tailf:display-when "not(../../ncs:module) or ../../ncs:module[ncs:name='tailf-ned-cisco-ios']";
      tailf:info
        "Modify enable password parameters";
      container password {
        tailf:info
          "Assign the privileged level password (MAX of 25 characters)";
        tailf:cli-compact-syntax;
        tailf:cli-sequence-commands;
        tailf:cli-reset-container;
        uses password-07-grouping;
      }
      leaf last-resort {
        tailf:info
          "Define enable action if no TACACS servers respond";
        tailf:cli-full-command;
        type enumeration {
          enum "password" {
            tailf:info
              "Enable by giving the local enable password";
          }
          enum "succeed" {
            tailf:info
              "Enable without further question";
          }
        }
      }
      container secret {
        tailf:info
          "Assign the privileged level secret";
        tailf:cli-compact-syntax;
        tailf:cli-sequence-commands;
        leaf level {
          tailf:info
            "Set exec level password";
          tailf:cli-optional-in-sequence;
          type uint8 {
            tailf:info
              "<1-15>;;Level number";
          }
        }
        leaf type {
          tailf:cli-drop-node-name;
          tailf:cli-optional-in-sequence;
          type enumeration {
            enum "0" {
              tailf:info
                "Specifies an UNENCRYPTED password will follow";
            }
            enum "4";
            enum "5" {
              tailf:info
                "Specifies an ENCRYPTED secret will follow";
            }
          }
        }
        leaf secret {
          tailf:cli-drop-node-name;
          type string {
            tailf:info
              "LINE;;The UNENCRYPTED (cleartext) 'enable' secret";
          }
        }
      }
      leaf use-tacacs {
        tailf:info
          "Use TACACS to check enable passwords";
        tailf:cli-full-command;
        type empty;
      }
    }
    container archive {
      tailf:ncs-device-type "cli-ned";
      tailf:display-when "not(../../ncs:module) or ../../ncs:module[ncs:name='tailf-ned-cisco-ios']";
      tailf:info
        "Archive the configuration";
      tailf:cli-add-mode;
      tailf:cli-mode-name "config-archive";
      container log {
        tailf:info
          "Logging commands";
        container config {
          tailf:info
            "Logging changes to the running configuration";
          tailf:cli-add-mode;
          tailf:cli-mode-name "config-archive-log-cfg";
          leaf hidekeys {
            tailf:info
              "suppress output (e.g. passwords) when displaying logged commands";
            type empty;
          }
        }
      }
    }
    list username {
      tailf:ncs-device-type "cli-ned";
      tailf:display-when "not(../ncs:module) or ../ncs:module[ncs:name='tailf-ned-cisco-ios']";
      tailf:info
        "Establish User Name Authentication";
      tailf:cli-suppress-mode;
      tailf:cli-delete-when-empty;
      tailf:cli-compact-syntax;
      key "name";
      leaf name {
        type string {
          tailf:info
            "WORD;;User name";
        }
      }
      container password {
        tailf:info
          "Specify the password for the user";
        tailf:cli-compact-syntax;
        tailf:cli-flatten-container;
        tailf:cli-sequence-commands;
        tailf:cli-reset-container;
        leaf encryption {
          tailf:cli-drop-node-name;
          tailf:cli-incomplete-command;
          tailf:cli-optional-in-sequence;
          type enumeration {
            enum "0" {
              tailf:info
                "Specifies an UNENCRYPTED password will follow";
            }
            enum "7" {
              tailf:info
                "Specifies a HIDDEN password will follow";
            }
          }
        }
        leaf password {
          tailf:cli-drop-node-name;
          tailf:cli-trim-default;
          type string {
            tailf:info
              "WORD;;The HIDDEN user password string";
          }
        }
      }
      leaf privilege {
        tailf:info
          "Set user privilege level";
        type uint8 {
          tailf:info
            "<0-15>;;User privilege level";
          range "0..15";
        }
      }
      container secret {
        tailf:info
          "Specify the secret for the user";
        tailf:cli-compact-syntax;
        tailf:cli-flatten-container;
        tailf:cli-sequence-commands;
        tailf:cli-reset-container;
        leaf encryption {
          tailf:cli-drop-node-name;
          tailf:cli-incomplete-command;
          tailf:cli-optional-in-sequence;
          type enumeration {
            enum "0" {
              tailf:info
                "Specifies an UNENCRYPTED secret will follow";
            }
            enum "5" {
              tailf:info
                "Specifies a HIDDEN secret will follow";
            }
          }
        }
        leaf secret {
          tailf:cli-drop-node-name;
          tailf:cli-trim-default;
          type string {
            tailf:info
              "WORD;;The HIDDEN user secret string";
          }
        }
      }
    }
    list controller {
      tailf:ncs-device-type "cli-ned";
      tailf:display-when "not(../ncs:module) or ../ncs:module[ncs:name='tailf-ned-cisco-ios']";
      tailf:info
        "Configure controller";
      tailf:cli-mode-name "config-controller";
      key "name number";
      leaf name {
        type enumeration {
          tailf:info
            "Controller name";
          enum "t1";
          enum "e1";
          enum "t3";
        }
      }
      leaf number {
        type string;
      }
      leaf framing {
        tailf:cli-full-command;
        type string;
      }
      container clock {
        container source {
          choice source-choice {
            container line {
              presence "true";
              leaf line-mode {
                tailf:cli-drop-node-name;
                tailf:cli-full-command;
                type enumeration {
                  enum "primary";
                  enum "secondary";
                }
              }
            }
            leaf internal {
              tailf:cli-full-command;
              type empty;
            }
            leaf loop-timed {
              tailf:cli-full-command;
              type empty;
            }
          }
        }
      }
      leaf linecode {
        tailf:cli-full-command;
        type enumeration {
          enum "ami";
          enum "b8zs";
          enum "hdb3";
        }
      }
      container cablelength {
        choice cablelength-choice {
          leaf long {
            tailf:cli-full-command;
            type string;
          }
          leaf short {
            tailf:cli-full-command;
            type string;
          }
        }
      }
      list channel-group {
        tailf:cli-suppress-mode;
        tailf:cli-delete-when-empty;
        key "number";
        leaf number {
          type uint8 {
            range "0..30";
          }
        }
        leaf-list timeslots {
          tailf:cli-replace-all;
          tailf:cli-range-list-syntax;
          type uint16;
        }
      }
    }
    container vrf {
      tailf:ncs-device-type "cli-ned";
      tailf:display-when "not(../../ncs:module) or ../../ncs:module[ncs:name='tailf-ned-cisco-ios']";
      tailf:info
        "VRF commands";
      list definition {
        tailf:info
          "VRF definition mode";
        tailf:cli-full-command;
        tailf:cli-mode-name "config-vrf";
        key "name";
        leaf name {
          tailf:info
            "WORD;;VRF name";
          type string;
        }
        leaf description {
          tailf:info
            "VRF specific description";
          tailf:cli-multi-value;
          type string {
            tailf:info
              "LINE;;Up to 244 characters describing this VRF";
            length "1..244";
          }
        }
        leaf rd {
          tailf:info
            "Specify Route Distinguisher";
          tailf:cli-full-command;
          type union {
            type string {
              tailf:info
                "ASN:nn or IP-address:nn;;VPN Route Distinguisher";
              pattern '[0-9]+:[0-9]+';
            }
            type inet:ipv4-address;
          }
        }
        container address-family {
          tailf:info
            "Enter Address Family command mode";
          container ipv4 {
            tailf:info
              "Address family";
            tailf:cli-exit-command "exit-address-family";
            tailf:cli-add-mode;
            presence "true";
            container export {
              tailf:info
                "VRF export";
              tailf:cli-incomplete-command;
              leaf map {
                tailf:info
                  "WORD;;Route-map reference";
                type string;
              }
            }
            container mdt {
              tailf:info
                "Backbone Multicast Distribution Tree";
              container default {
                tailf:info
                  "The default group";
                leaf address {
                  tailf:cli-drop-node-name;
                  tailf:cli-full-command;
                  tailf:cli-remove-before-change;
                  type inet:ipv4-address {
                    tailf:info
                      "A.B.C.D;;IP multicast group address";
                  }
                }
                container mpls {
                  tailf:info
                    "MPLS tunnel options";
                  leaf mldp {
                    tailf:info
                      "Use a MLDP LSP to create the default MDT";
                    type inet:ipv4-address {
                      tailf:info
                        "A.B.C.D;;MP2MP LSP root address";
                    }
                  }
                }
              }
              container data {
                tailf:info
                  "MDT data trees";
                list multicast {
                  tailf:cli-drop-node-name;
                  tailf:cli-suppress-mode;
                  tailf:cli-delete-when-empty;
                  key "address wildcard";
                  leaf address {
                    type inet:ipv4-address {
                      tailf:info
                        "A.B.C.D;;  IP multicast group address";
                    }
                  }
                  leaf wildcard {
                    type inet:ipv4-address {
                      tailf:info
                        "A.B.C.D;;Wildcard bits";
                    }
                  }
                }
                leaf list {
                  tailf:info
                    "Access-list";
                  type ext-acl-type;
                }
                leaf threshold {
                  tailf:info
                    "MDT switching threshold";
                  type uint32 {
                    tailf:info
                      "<1-4294967>;;Traffic rate in kilobits per second";
                  }
                }
              }
              leaf log-reuse {
                tailf:info
                  "Event logging for data MDT reuse";
                type empty;
              }
              leaf-list preference {
                tailf:info
                  "MDT preference (default pim mldp)";
                tailf:cli-flat-list-syntax {
                  tailf:cli-replace-all;
                }
                type enumeration {
                  enum "mldp" {
                    tailf:info
                      "MDT preference mLDP";
                  }
                  enum "pim" {
                    tailf:info
                      "MDT preference PIM";
                  }
                }
              }
            }
            container route-target {
              tailf:info
                "Specify Target VPN Extended Communities";
              uses vrf-route-target-grouping;
            }
          }
          container ipv6 {
            tailf:info
              "Address family";
            tailf:cli-exit-command "exit-address-family";
            tailf:cli-add-mode;
            presence "true";
            container route-target {
              tailf:info
                "Specify Target VPN Extended Communities";
              uses vrf-route-target-grouping;
            }
          }
        }
        container route-target {
          tailf:info
            "Specify Target VPN Extended Communities";
          uses vrf-route-target-grouping;
        }
      }
    }
    container ip {
      tailf:ncs-device-type "cli-ned";
      tailf:display-when "not(../../ncs:module) or ../../ncs:module[ncs:name='tailf-ned-cisco-ios']";
      tailf:info
        "Global IP configuration subcommands";
      leaf subnet-zero {
        tailf:info
          "Allow 'subnet zero' subnets";
        type empty;
      }
      list vrf {
        tailf:info
          "Configure an IP VPN Routing/Forwarding instance";
        tailf:cli-mode-name "config-vrf";
        key "name";
        leaf name {
          tailf:info
            "WORD;;VPN Routing/Forwarding instance name";
          type string;
        }
        container bgp {
          tailf:info
            "Commands pertaining to BGP";
          container next-hop {
            tailf:info
              "Next-hop for the routes of a VRF in the backbone";
            leaf Loopback {
              tailf:info
                "Loopback interface number";
              type uint32 {
                tailf:info
                  "<0-2147483647>;;Loopback interface number";
                range "0..2147483647";
              }
            }
          }
        }
        leaf context {
          tailf:info
            "Associate SNMP context with this vrf";
          type string {
            tailf:info
              "WORD;;SNMP Context Name";
          }
        }
        leaf description {
          tailf:info
            "VRF specific description";
          tailf:cli-multi-value;
          type string {
            length "1..244";
            tailf:info
              "LINE;;Up to 244 characters describing this VRF";
          }
        }
        container export {
          tailf:info
            "VRF export";
          leaf map {
            tailf:info
              "Route-map based VRF export";
            type string {
              tailf:info
                "WORD;;VRF export route-map name";
            }
          }
        }
        container import {
          tailf:info
            "VRF import";
          choice import-choice {
            leaf map {
              tailf:info
                "Route-map based VRF import";
              type string {
                tailf:info
                  "WORD;;VRF import route-map name";
              }
            }
            container ipv4 {
              tailf:cli-compact-syntax;
              tailf:cli-sequence-commands;
              tailf:info
                "Address family based VRF import";
              leaf ipv4-type {
                tailf:cli-drop-node-name;
                type enumeration {
                  enum "unicast" {
                    tailf:code-name "ipv41_unicast";
                    tailf:info
                      "Import prefixes from IPv4 Unicast table";
                  }
                  enum "multicast" {
                    tailf:code-name "ipv41_multicast";
                    tailf:info
                      "Import prefixes from IPv4 Multicast tabl";
                  }
                }
              }
              leaf upper-limit {
                tailf:cli-break-sequence-commands;
                tailf:cli-drop-node-name;
                type uint32 {
                  range "1..2147483647";
                  tailf:info
                    "<1-2147483647>;;Upper limit on import prefixes without hogging memory";
                }
              }
              leaf map {
                tailf:info
                  "Route-map based VRF import";
                type string {
                  tailf:info
                    "WORD;;VRF import route-map name";
                }
              }
            }
          }
        }
        container maximum {
          tailf:info
            "Maximum number of routes allowed in this routing table";
          tailf:cli-incomplete-command;
          tailf:cli-compact-syntax;
          tailf:cli-sequence-commands;
          presence "Maximum number of routes allowed in this routing table";
          leaf routes {
            tailf:info
              "Maximum number of routes allowed in this routing table";
            tailf:cli-incomplete-command;
            type uint32 {
              range "1..4294967295";
              tailf:info
                "<1-4294967295>;;Maximum number of routes allowed";
            }
          }
          choice maximum-choice {
            mandatory true;
            case threshold-case {
              leaf threshold {
                tailf:cli-drop-node-name;
                tailf:info
                  "";
                type uint16 {
                  range "1..100";
                  tailf:info
                    "<1-100>;;Threshold value (%) at which to generate a warning msg";
                }
              }
              leaf reinstall {
                tailf:info
                  "Reinstall previous rejected route due to over maximum route limit";
                type uint16 {
                  range "1..100";
                  tailf:info
                    "<1-100>;;Threshold value (%) at which to reinstall routes back to VRF";
                }
              }
            }
            case warning-case {
              leaf warning-only {
                tailf:info
                  "Only give a warning message if is limit exceeded";
                type empty;
              }
            }
          }
        }
        container mdt {
          tailf:info
            "Backbone Multicast Distribution Tree";
          tailf:cli-incomplete-command;
          presence "Backbone Multicast Distribution Tree";
          leaf default {
            tailf:info
              "The default group";
            type inet:ipv4-address {
              tailf:info
                "A.B.C.D;;IP multicast group address";
            }
          }
          leaf log-reuse {
            tailf:info
              "Event logging for data MDT reuse";
            type empty;
          }
          container data {
            tailf:info
              "MDT data group range";
            tailf:cli-compact-syntax;
            tailf:cli-sequence-commands;
            tailf:cli-incomplete-command;
            leaf mulicast-address {
              tailf:cli-drop-node-name;
              tailf:cli-incomplete-command;
              type inet:ipv4-address {
                tailf:info
                  "A.B.C.D;;IP multicast group address";
              }
            }
            leaf wildcard-bits {
              tailf:cli-drop-node-name;
              type inet:ipv4-address {
                tailf:info
                  "A.B.C.D;;Wildcard bits";
              }
            }
            choice mdt-data-choice {
              case mdt-data-threshold {
                leaf threshold {
                  tailf:info
                    "MDT switching threshold";
                  type uint32 {
                    tailf:info
                      "<1-4294967>;;Traffic rate in kilobits per second";
                    range "1..4294967";
                  }
                }
                leaf threshold-list {
                  tailf:alt-name "list";
                  tailf:info
                    "Access-list";
                  type mdt-data-list-type;
                }
              }
              case mdt-data-list {
                leaf list {
                  tailf:info
                    "Access-list";
                  type mdt-data-list-type;
                }
              }
            }
          }
        }
        leaf rd {
          tailf:info
            "Specify Route Distinguisher";
          type rd-type;
        }
        list route-target {
          tailf:info
            "Specify Target VPN Extended Communities";
          tailf:cli-suppress-mode;
          tailf:cli-delete-when-empty;
          key "direction target";
          leaf direction {
            type enumeration {
              enum "both" {
                tailf:info
                  "Both import and export Target-VPN community";
              }
              enum "export" {
                tailf:code-name "direction_export";
                tailf:info
                  "Export Target-VPN community";
              }
              enum "import" {
                tailf:code-name "direction_import";
                tailf:info
                  "Import Target-VPN community";
              }
            }
          }
          leaf target {
            type rd-type {
              tailf:info
                "ASN:nn or IP-address:nn;;Target VPN Extended Community";
            }
          }
        }
        container vpn {
          tailf:info
            "Configure VPN ID as specified in rfc2685";
          leaf id {
            tailf:info
              "Configure VPN ID in rfc2685 format";
            type vpn-id-type;
          }
        }
      }
      container mcr-conf {
        tailf:cli-no-keyword;
        tailf:cli-drop-node-name;
        leaf multicast-routing {
          tailf:info
            "Enable IP multicast forwarding";
          type empty;
        }
      }
      container multicast-routing {
        tailf:info
          "Enable IP multicast forwarding";
        tailf:cli-incomplete-no;
        tailf:cli-incomplete-command;
        tailf:cli-diff-dependency "/ios:ip/vrf" {
          tailf:xpath-root 3;
        }
        tailf:cli-diff-dependency "/ios:vrf/definition" {
          tailf:xpath-root 3;
        }
        tailf:cli-diff-dependency "../mcr-conf/multicast-routing" {
          tailf:xpath-root 3;
        }
        list vrf {
          tailf:info
            "Select VPN Routing/Forwarding instance";
          tailf:cli-suppress-list-no;
          tailf:cli-suppress-mode;
          tailf:cli-delete-when-empty;
          tailf:cli-compact-syntax;
          tailf:cli-reset-container;
          tailf:cli-diff-dependency "../../mcr-conf/multicast-routing" {
            tailf:xpath-root 3;
          }
          key "name";
          leaf name {
            type string {
              tailf:info
                "WORD;;VPN Routing/Forwarding instance name";
            }
          }
          leaf distributed {
            tailf:info
              "Distributed multicast switching";
            type empty;
          }
        }
        leaf distributed {
          tailf:info
            "Distributed multicast switching";
          tailf:cli-full-command;
          type empty;
        }
      }
      container as-path {
        tailf:info
          "BGP autonomous system path filter";
        list access-list {
          tailf:info
            "Specify an access list number";
          tailf:cli-suppress-mode;
          tailf:cli-delete-when-empty;
          tailf:cli-incomplete-command;
          tailf:cli-compact-syntax;
          key "name";
          leaf name {
            tailf:cli-incomplete-command;
            type uint16 {
              range "1..500";
              tailf:info
                "<1-500>;;AS path access list number";
            }
          }
          list as-path-rule {
            tailf:cli-suppress-mode;
            tailf:cli-delete-when-empty;
            tailf:cli-drop-node-name;
            tailf:cli-compact-syntax;
            tailf:cli-show-long-obu-diffs;
            ordered-by user;
            key "operation rule";
            leaf operation {
              tailf:cli-drop-node-name;
              tailf:cli-incomplete-command;
              type enumeration {
                enum "deny" {
                  tailf:code-name "operation_deny";
                  tailf:info
                    "Specify packets to reject";
                }
                enum "permit" {
                  tailf:code-name "operation_permit";
                  tailf:info
                    "Specify packets to forward";
                }
              }
            }
            leaf rule {
              tailf:cli-drop-node-name;
              tailf:cli-multi-value;
              tailf:cli-full-command;
              type string {
                tailf:info
                  "LINE;;A regular-expression to match BGP AS paths.";
              }
            }
          }
        }
      }
      container local {
        tailf:info
          "Specify local options";
        list pool {
          tailf:info
            "IP Local address pool lists";
          tailf:cli-suppress-mode;
          tailf:cli-delete-when-empty;
          tailf:cli-compact-syntax;
          tailf:cli-sequence-commands {
            tailf:cli-reset-siblings;
          }
          key "id";
          leaf id {
            type union {
              type string {
                tailf:info
                  "WORD;;Create named local address pool";
              }
              type enumeration {
                enum "default" {
                  tailf:info
                    "Create default local address pool";
                }
              }
            }
          }
          leaf start {
            tailf:cli-drop-node-name;
            type inet:ipv4-address {
              tailf:info
                "A.B.C.D;;First IP address of range";
            }
          }
          leaf last {
            tailf:cli-drop-node-name;
            tailf:cli-optional-in-sequence;
            type inet:ipv4-address {
              tailf:info
                "A.B.C.D;;Last IP address of range";
            }
          }
          leaf group {
            tailf:info
              "Create ip local pool group";
            type string {
              tailf:info
                "WORD;;Group name for this named local address pool";
            }
          }
        }
      }
      container cef {
        tailf:info
          "Cisco Express Forwarding";
        presence "true";
        leaf distributed {
          tailf:info
            "Distributed Cisco Express Forwarding";
          tailf:cli-full-command;
          type empty;
        }
      }
      leaf classless {
        tailf:info
          "Follow classless routing forwarding rules";
        type empty;
      }
      container community-list {
        tailf:info
          "Add a community list entry";
        list number-standard {
          tailf:cli-drop-node-name;
          tailf:cli-incomplete-command;
          tailf:cli-suppress-mode;
          tailf:cli-delete-when-empty;
          key "no";
          leaf no {
            type uint16 {
              range "1..99";
              tailf:info
                "<1-99>;;Community list number (standard)";
            }
          }
          uses ip-community-list-standard-grouping;
        }
        list number-expanded {
          tailf:cli-drop-node-name;
          tailf:cli-incomplete-command;
          tailf:cli-suppress-mode;
          tailf:cli-delete-when-empty;
          key "no";
          leaf no {
            type uint16 {
              range "100..500";
              tailf:info
                "<100-500>;;Community list number (expanded)";
            }
          }
          uses ip-community-list-expanded-grouping;
        }
        list expanded {
          tailf:info
            "Add an expanded community-list entry";
          tailf:cli-incomplete-command;
          tailf:cli-suppress-mode;
          tailf:cli-delete-when-empty;
          key "name";
          leaf name {
            type string {
              tailf:info
                "WORD;;Community list name";
            }
          }
          uses ip-community-list-expanded-grouping;
        }
        list standard {
          tailf:info
            "Add a standard community-list entry";
          tailf:cli-incomplete-command;
          tailf:cli-suppress-mode;
          tailf:cli-delete-when-empty;
          key "name";
          leaf name {
            type string {
              tailf:info
                "WORD;;Community list name";
            }
          }
          uses ip-community-list-standard-grouping;
        }
      }
      container domain {
        tailf:info
          "IP DNS Resolver";
        leaf list {
          tailf:info
            "Domain name to complete unqualified host names";
          type string {
            tailf:info
              "WORD;;A domain name";
          }
        }
        leaf lookup {
          tailf:info
            "Enable IP Domain Name System hostname translation";
          tailf:cli-boolean-no;
          tailf:cli-trim-default;
          type boolean;
          default "true";
        }
        container lookup-settings {
          tailf:cli-drop-node-name;
          container lookup {
            tailf:info
              "Enable IP Domain Name System hostname translation";
            leaf nsap {
              tailf:info
                "Enable IP DNS queries for CLNS NSAP addresses";
              tailf:cli-full-command;
              type empty;
            }
            container source-interface {
              tailf:info
                "Specify source interface for DNS resolver";
              tailf:cli-diff-dependency "/ios:interface" {
                tailf:xpath-root 3;
              }
              uses interface-grouping;
            }
          }
          leaf name {
            tailf:info
              "Define the default domain name";
            type string {
              tailf:info
                "WORD;;Default domain name";
            }
          }
        }
        leaf name {
          tailf:info
            "Define the default domain name";
          type string {
            tailf:info
              "WORD;;Default domain name";
          }
        }
      }
      container domain-lookup {
        tailf:info
          "Enable IP Domain Name System hostname translation";
        tailf:cli-show-no;
        presence "true";
        leaf nsap {
          tailf:info
            "Enable IP DNS queries for CLNS NSAP addresses";
          type empty;
        }
        container source-interface {
          tailf:info
            "Specify source interface for DNS resolver";
          tailf:cli-diff-dependency "/ios:interface" {
            tailf:xpath-root 3;
          }
          uses interface-grouping;
        }
      }
      leaf domain-name {
        tailf:info
          "Define the default domain name";
        type string {
          tailf:info
            "WORD;;Default domain name";
        }
      }
      container dns {
        tailf:info
          "Configure DNS server for a zone";
        container server {
          tailf:info
            "Enable DNS server";
          presence "true";
        }
      }
      leaf default-gateway {
        tailf:info
          "Specify default gateway (if not routing IP)";
        type inet:ipv4-address {
          tailf:info
            "A.B.C.D;;IP address of default gateway";
        }
      }
      container dhcp {
        tailf:info
          "Configure DHCP server and relay parameters";
        list class {
          tailf:info
            "Configure DHCP classes";
          key "id";
          leaf id {
            type string {
              tailf:info
                "WORD;;Class name";
            }
          }
          container relay {
            tailf:info
              "Enter relay agent information option configuration submode";
            container agent {
              tailf:info
                "Enter relay agent information option configuration submode";
              leaf information {
                tailf:info
                  "Enter relay agent information option configuration submode";
                type empty;
              }
            }
          }
          leaf remark {
            tailf:info
              "Specify a remark for this class";
            tailf:cli-multi-value;
            type string {
              tailf:info
                "LINE;;Up to 240 characters describing this class";
              length "1..240";
            }
          }
        }
        list pool {
          tailf:info
            "Configure DHCP address pools";
          key "id";
          leaf id {
            type string {
              tailf:info
                "WORD;;Pool name";
            }
          }
        }
        leaf smart-relay {
          tailf:info
            "Enable Smart Relay feature";
          type empty;
        }
        container snooping {
          tailf:info
            "DHCP Snooping";
          presence "true";
          tailf:cli-display-separated;
          container information {
            tailf:info
              "DHCP Snooping information";
            container option {
              tailf:info
                "DHCP Snooping information option";
              presence "true";
              leaf allow-untrusted {
                tailf:info
                  "DHCP Snooping information option allow-untrusted";
                type empty;
              }
              container format {
                tailf:info
                  "Option 82 information format";
                container remote-id {
                  tailf:info
                    "Remote id option 82 format";
                  choice remote-id-choice {
                    leaf hostname {
                      tailf:info
                        "Use configured hostname for remote id";
                      type empty;
                    }
                    leaf string {
                      tailf:info
                        "User defined string for remote id";
                      type string {
                        tailf:info
                          "WORD;;Use string for remote id (max length 63)";
                      }
                    }
                  }
                }
              }
            }
          }
          container track {
            tailf:info
              "DHCP snooping track";
            leaf host {
              tailf:info
                "DHCP snooping track host";
              type empty;
            }
          }
          container verify {
            tailf:info
              "DHCP snooping verify";
            leaf mac-address {
              tailf:info
                "DHCP snooping verify mac-address";
              type empty;
            }
            leaf no-relay-agent-address {
              tailf:info
                "DHCP snooping verify giaddr";
              type empty;
            }
          }
          leaf-list vlan {
            tailf:info
              "DHCP Snooping vlan";
            type uint16 {
              tailf:info
                "WORD;;DHCP Snooping vlan fist number or vlan range, example: 1,3-5,7,9-11";
            }
          }
        }
      }
      container flow-cache {
        tailf:info
          "Configure netflow cache parameters";
        container timeout {
          tailf:info
            "Specify flow cache timeout parameters";
          leaf active {
            tailf:info
              "Specify the active flow timeout";
            type uint16 {
              tailf:info
                "<1-60>;;Timeout in minutes";
              range "1..60";
            }
          }
        }
      }
      container flow-export {
        tailf:info
          "Specify host/port to send flow statistics";
        container destination {
          tailf:info
            "Specify the Destination IP address";
          tailf:cli-sequence-commands {
            tailf:cli-reset-all-siblings;
          }
          tailf:cli-compact-syntax;
          leaf ip {
            tailf:cli-drop-node-name;
            type host-type {
              tailf:info
                "Hostname or A.B.C.D  Destination IP address";
            }
          }
          leaf port {
            tailf:cli-drop-node-name;
            type uint16 {
              tailf:info
                "<1-65535>;;UDP port number";
              range "1..65535";
            }
          }
        }
        container source {
          tailf:info
            "Specify the interface for source address";
          tailf:cli-diff-dependency "/ios:interface" {
            tailf:xpath-root 3;
          }
          uses interface-grouping;
        }
        leaf version {
          tailf:info
            "Specify the version number";
          type enumeration {
            enum "1";
            enum "5";
            enum "9";
          }
        }
      }
      container forward-protocol {
        tailf:info
          "Controls forwarding of physical and directed IP broadcasts";
        choice protocol-choice {
          leaf protocol {
            tailf:cli-drop-node-name;
            type enumeration {
              enum "nd" {
                tailf:info
                  "Sun's Network Disk protocol";
              }
              enum "sdns" {
                tailf:info
                  "Network Security Protocol";
              }
              enum "turbo-flood" {
                tailf:info
                  "Fast flooding of UDP broadcasts";
              }
            }
          }
          container spanning-tree {
            tailf:info
              "Use transparent bridging to flood UDP broadcasts";
            presence "true";
            leaf any-local-broadcast {
              tailf:info
                "Accept any local broadcast when flooding";
              type empty;
            }
          }
          leaf udp {
            tailf:info
              "Packets to a specific UDP port";
            type string;
          }
        }
      }
      container ftp {
        tailf:info
          "FTP configuration commands";
        container source-interface {
          tailf:info
            "Specify interface for source address in FTP connections";
          tailf:cli-diff-dependency "/ios:interface" {
            tailf:xpath-root 3;
          }
          uses interface-grouping;
        }
        leaf passive {
          tailf:info
            "Connect using passive mode";
          type empty;
        }
        container password {
          tailf:info
            "Specify password for FTP connections;";
          uses password-grouping;
        }
        leaf username {
          tailf:info
            "Specify username for FTP connections";
          type string;
        }
      }
      container telnet {
        tailf:info
          "Specify telnet options";
        leaf source-interface {
          tailf:info
            "Specify source interface";
          type string;
        }
      }
      container http {
        tailf:info
          "HTTP server configuration";
        leaf access-class {
          tailf:info
            "Restrict http server access by access-class";
          tailf:cli-full-command;
          type uint8 {
            tailf:info
              "<1-99>;;Access list number";
            range "1..99";
          }
        }
        container authentication {
          tailf:info
            "Set http server authentication method";
          choice authentication-choice {
            leaf aaa {
              tailf:info
                "Use AAA access control methods";
              tailf:cli-full-command;
              type empty;
            }
            leaf local {
              tailf:info
                "Use local username and passwords";
              tailf:cli-full-command;
              type empty;
            }
          }
        }
        leaf server {
          tailf:info
            "Enable http server";
          tailf:cli-boolean-no;
          tailf:cli-show-with-default;
          tailf:cli-full-command;
          type boolean;
        }
        leaf secure-server {
          tailf:info
            "Enable HTTP secure server";
          tailf:cli-boolean-no;
          tailf:cli-show-with-default;
          tailf:cli-full-command;
          type boolean;
          default "false";
        }
        container timeout-policy {
          tailf:info
            "Set http server time-out policy parameters";
          tailf:cli-compact-syntax;
          tailf:cli-reset-container;
          tailf:cli-sequence-commands;
          leaf idle {
            tailf:info
              "Idle time-out of a http server connection in seconds";
            tailf:cli-incomplete-command;
            type uint16 {
              tailf:info
                "<1-600>;;Connection idle time-out value in seconds";
              range "1..600";
            }
          }
          leaf life {
            tailf:info
              "Life time of a http server connection in seconds";
            tailf:cli-incomplete-command;
            type uint32 {
              tailf:info
                "<1-86400>;;Connection life time value in seconds";
              range "1..86400";
            }
          }
          leaf requests {
            tailf:info
              "Maximum number of requests allowed on a http server connection";
            type uint32 {
              tailf:info
                "<1-86400>;;Maximum number of requests allowed on a http server connection";
              range "1..86400";
            }
          }
        }
        container client {
          tailf:info
            "Set http client parameters";
          tailf:cli-incomplete-command;
          leaf source-interface {
            tailf:cli-full-command;
            tailf:cli-multi-value;
            tailf:info
              "Specify interface for source address in all HTTP(S) client connections";
            type string {
              tailf:info
                "WORD;;Interface name";
            }
          }
        }
      }
      container igmp {
        tailf:info
          "IGMP global configuration";
        container snooping {
          tailf:info
            "Global IGMP Snooping enable for Catalyst Vlans";
          presence "true";
          leaf l2-entry-limit {
            tailf:info
              "limit on the l2 entry that can be installed by IGMP snooping";
            type uint32 {
              tailf:info
                "<1-100000>;;maximum number of l2 entries";
              range "1..100000";
            }
          }
        }
      }
      container multicast {
        tailf:info
          "Global IP Multicast Commands";
        leaf multipath {
          tailf:info
            "RPF across equal-cost paths";
          type empty;
        }
      }
      container nat {
        tailf:info
          "NAT configuration commands";
        tailf:cli-diff-dependency "/ios:ip/vrf" {
          tailf:xpath-root 3;
        }
        tailf:cli-diff-dependency "/ios:vrf/definition" {
          tailf:xpath-root 3;
        }
        tailf:cli-diff-dependency "/ios:vrf/definition/address-family" {
          tailf:xpath-root 3;
        }
        list pool {
          tailf:info
            "Define pool of addresses";
          tailf:cli-suppress-mode;
          tailf:cli-delete-when-empty;
          tailf:cli-compact-syntax;
          tailf:cli-sequence-commands {
            tailf:cli-reset-siblings;
          }
          key "id";
          leaf id {
            type string {
              tailf:info
                "WORD;;Pool name";
            }
          }
          leaf start-address {
            tailf:cli-drop-node-name;
            tailf:cli-optional-in-sequence;
            type inet:ipv4-address {
              tailf:info
                "A.B.C.D;;Start IP address";
            }
          }
          leaf end-address {
            tailf:cli-drop-node-name;
            when '../start-address' {
              tailf:xpath-root 3;
              tailf:dependency "../start-address";
            }
            type inet:ipv4-address {
              tailf:info
                "A.B.C.D;;End IP address";
            }
          }
          choice prefix-choice {
            leaf netmask {
              tailf:info
                "Specify the network mask";
              type inet:ipv4-address {
                tailf:info
                  "A.B.C.D;;Network mask";
              }
            }
            leaf prefix-length {
              tailf:info
                "Specify the prefix length";
              type uint8 {
                tailf:info
                  "<1-32>;;Prefix length";
                range "1..32";
              }
            }
          }
          leaf accounting {
            tailf:cli-optional-in-sequence;
            tailf:info
              "Specify the accounting";
            type string {
              tailf:info
                "WORD;;Accounting method-list name";
            }
          }
          choice nat-choice {
            leaf arp-ping {
              tailf:info
                "WLAN ARP Ping";
              type empty;
            }
            leaf type {
              tailf:info
                "Specify the pool type";
              type enumeration {
                enum "match-host" {
                  tailf:info
                    "Keep host numbers the same after translation";
                }
                enum "rotary" {
                  tailf:info
                    "Rotary address pool";
                }
              }
            }
            leaf add-route {
              tailf:info
                "Add special route to Virtual Interface";
              type empty;
            }
          }
        }
        container inside {
          tailf:info
            "Inside address translation";
          container source {
            tailf:info
              "Source address translation";
            list list {
              tailf:info
                "Specify access list describing local addresses";
              tailf:cli-suppress-mode;
              tailf:cli-delete-when-empty;
              tailf:cli-compact-syntax;
              tailf:cli-sequence-commands {
                tailf:cli-reset-all-siblings;
              }
              tailf:cli-incomplete-command;
              key "id";
              leaf id {
                type union {
                  type uint16 {
                    tailf:info
                      "<1-2699>;;Access list number for global addresses";
                    range "1..2699";
                  }
                  type string {
                    tailf:info
                      "WORD;;Access list name for global addresses";
                  }
                }
              }
              choice pool-or-interface {
                case pool-choice {
                  leaf pool {
                    tailf:info
                      "Name pool of global addresses";
                    type string;
                    tailf:non-strict-leafref {
                      path "/ncs:devices/ncs:device/ncs:config/ios:ip/nat/pool/id" {
                        tailf:xpath-root 3;
                      }
                    }
                  }
                  leaf redundancy {
                    tailf:info
                      "NAT redundancy operation";
                    tailf:cli-optional-in-sequence;
                    type uint8 {
                      tailf:info
                        "<1-2>;;IP redundancy ID";
                      range "1..2";
                    }
                  }
                  leaf mapping-id {
                    tailf:info
                      "Associate a mapping id to this mapping";
                    tailf:cli-optional-in-sequence;
                    type uint32 {
                      tailf:info
                        "<1-2147483647>;;Stateful NAT mapping id";
                      range "1..2147483647";
                    }
                  }
                }
                case interface-choice {
                  container interface {
                    tailf:info
                      "Specify interface for global address";
                    tailf:cli-compact-syntax;
                    tailf:cli-flatten-container;
                    uses interface-grouping;
                  }
                }
              }
              leaf no-payload {
                tailf:info
                  "No translation of embedded address/port in the payload";
                tailf:cli-optional-in-sequence;
                type empty;
              }
              leaf reversible {
                tailf:cli-optional-in-sequence;
                type empty;
              }
              leaf vrf {
                tailf:info
                  "Specify vrf";
                tailf:cli-optional-in-sequence;
                type string {
                  tailf:info
                    "WORD;;vrf name";
                }
              }
              leaf match-in-vrf {
                when '../vrf' {
                  tailf:xpath-root 3;
                }
                tailf:info
                  "Match incoming vrf";
                tailf:cli-optional-in-sequence;
                type empty;
              }
              leaf overload {
                tailf:info
                  "Overload an address translation";
                tailf:cli-optional-in-sequence;
                type empty;
              }
              leaf oer {
                tailf:info
                  "Use with vtemplate only. On new translation, if OER BR is UP, OER will select IP from outgoing Interface. All packets matching translation are forwarded over Interface for duration of translation.";
                type empty;
              }
            }
            container static {
              tailf:info
                "Specify static local->global mapping";
              list nat-static-transport-list {
                tailf:cli-drop-node-name;
                tailf:cli-suppress-mode;
                tailf:cli-delete-when-empty;
                tailf:cli-compact-syntax;
                tailf:cli-sequence-commands {
                  tailf:cli-reset-siblings;
                }
                key "proto local-ip local-port global-ip global-port";
                leaf proto {
                  type enumeration {
                    enum "tcp" {
                      tailf:info
                        "Transmission Control Protocol";
                    }
                    enum "udp" {
                      tailf:info
                        "User Datagram Protocol";
                    }
                  }
                }
                leaf local-ip {
                  tailf:cli-drop-node-name;
                  type inet:ipv4-address {
                    tailf:info
                      "A.B.C.D;;Inside local IP address";
                  }
                }
                leaf local-port {
                  tailf:cli-drop-node-name;
                  type uint16 {
                    tailf:info
                      "<1-65535>;;Local UDP/TCP port";
                    range "1..65535";
                  }
                }
                leaf global-ip {
                  tailf:cli-drop-node-name;
                  type inet:ipv4-address {
                    tailf:info
                      "A.B.C.D;;Inside global IP address";
                  }
                }
                leaf global-port {
                  tailf:cli-drop-node-name;
                  type uint16 {
                    tailf:info
                      "<1-65535>;;Global UDP/TCP port";
                    range "1..65535";
                  }
                }
                leaf extendable {
                  tailf:info
                    "Extend this translation when used";
                  tailf:cli-optional-in-sequence;
                  type empty;
                }
                leaf no-alias {
                  tailf:info
                    "Do not create an alias for the global address";
                  tailf:cli-optional-in-sequence;
                  type empty;
                }
                leaf no-payload {
                  tailf:info
                    "No translation of embedded address/port in the payload";
                  tailf:cli-optional-in-sequence;
                  type empty;
                }
                leaf route-map {
                  tailf:info
                    "Specify route-map";
                  tailf:cli-optional-in-sequence;
                  type string {
                    tailf:info
                      "WORD;;Route-map name";
                  }
                }
                leaf reversible {
                  when '../route-map' {
                    tailf:xpath-root 3;
                  }
                  tailf:cli-optional-in-sequence;
                  type empty;
                }
                leaf redundancy {
                  tailf:info
                    "NAT redundancy operation";
                  tailf:cli-optional-in-sequence;
                  type union {
                    type uint8 {
                      tailf:info
                        "<1-2>;IP redundancy ID";
                    }
                    type string {
                      tailf:info
                        "WORD;;IP redundancy name";
                    }
                  }
                }
                leaf mapping-id {
                  when '../redundancy' {
                    tailf:xpath-root 3;
                  }
                  tailf:info
                    "Associate a mapping id to this mapping";
                  tailf:cli-optional-in-sequence;
                  type uint32 {
                    tailf:info
                      "<1-2147483647>;;Stateful NAT mapping id";
                    range "1..2147483647";
                  }
                }
                leaf vrf {
                  tailf:info
                    "Specify vrf";
                  tailf:cli-optional-in-sequence;
                  type string {
                    tailf:info
                      "WORD;;vrf name";
                  }
                }
                leaf match-in-vrf {
                  when '../vrf' {
                    tailf:xpath-root 3;
                  }
                  tailf:info
                    "Match incoming vrf";
                  tailf:cli-optional-in-sequence;
                  type empty;
                }
                leaf forced {
                  tailf:info
                    "Delete this entry and its children, even if in use";
                  tailf:cli-optional-in-sequence;
                  type empty;
                }
                leaf overload {
                  tailf:info
                    "Overload an address translation";
                  type empty;
                }
              }
              list nat-static-transport-interface-list {
                tailf:cli-drop-node-name;
                tailf:cli-suppress-mode;
                tailf:cli-delete-when-empty;
                tailf:cli-compact-syntax;
                tailf:cli-sequence-commands {
                  tailf:cli-reset-siblings;
                }
                tailf:cli-incomplete-command;
                key "proto local-ip local-port";
                leaf proto {
                  type enumeration {
                    enum "tcp" {
                      tailf:info
                        "Transmission Control Protocol";
                    }
                    enum "udp" {
                      tailf:info
                        "User Datagram Protocol";
                    }
                  }
                }
                leaf local-ip {
                  tailf:cli-drop-node-name;
                  type inet:ipv4-address {
                    tailf:info
                      "A.B.C.D;;Inside local IP address";
                  }
                }
                leaf local-port {
                  tailf:cli-drop-node-name;
                  type uint16 {
                    tailf:info
                      "<1-65535>;;Local UDP/TCP port";
                    range "1..65535";
                  }
                }
                container interface {
                  tailf:info
                    "Specify interface for global address";
                  tailf:cli-compact-syntax;
                  tailf:cli-flatten-container;
                  uses interface-grouping;
                }
                leaf global-port {
                  tailf:cli-drop-node-name;
                  type uint16 {
                    tailf:info
                      "<1-65535>;;Global UDP/TCP port";
                    range "1..65535";
                  }
                }
              }
            }
          }
          container destination {
            tailf:info
              "Destination address translation";
            list list {
              tailf:info
                "Specify access list describing global addresses";
              tailf:cli-suppress-mode;
              tailf:cli-delete-when-empty;
              tailf:cli-compact-syntax;
              tailf:cli-sequence-commands {
                tailf:cli-reset-siblings;
              }
              tailf:cli-incomplete-command;
              key "id";
              leaf id {
                type union {
                  type uint16 {
                    tailf:info
                      "<1-2699>;;Access list number for global addresses";
                    range "1..2699";
                  }
                  type string {
                    tailf:info
                      "WORD;;Access list name for global addresses";
                  }
                }
              }
              leaf pool {
                tailf:info
                  "Name pool of local addresses";
                type string;
                tailf:non-strict-leafref {
                  path "/ncs:devices/ncs:device/ncs:config/ios:ip/nat/pool/id" {
                    tailf:xpath-root 3;
                  }
                }
              }
              leaf redundancy {
                tailf:info
                  "NAT redundancy operation";
                tailf:cli-optional-in-sequence;
                type uint8 {
                  tailf:info
                    "<1-2>;;IP redundancy ID";
                  range "1..2";
                }
              }
              leaf mapping-id {
                tailf:info
                  "Associate a mapping id to this mapping";
                type uint32 {
                  tailf:info
                    "<1-2147483647>;;Stateful NAT mapping id";
                  range "1..2147483647";
                }
              }
            }
          }
        }
        container outside {
          tailf:info
            "Outside address translation";
          list list {
            tailf:info
              "Specify access list describing global addresses";
            tailf:cli-suppress-mode;
            tailf:cli-delete-when-empty;
            tailf:cli-compact-syntax;
            tailf:cli-sequence-commands {
              tailf:cli-reset-siblings;
            }
            key "id";
            leaf id {
              type union {
                type uint16 {
                  tailf:info
                    "<1-2699>;;Access list number for global addresses";
                  range "1..2699";
                }
                type string {
                  tailf:info
                    "WORD;;Access list name for global addresses";
                }
              }
            }
            leaf pool {
              tailf:info
                "Name pool of local addresses";
              type string;
              tailf:non-strict-leafref {
                path "/ncs:devices/ncs:device/ncs:config/ios:ip/nat/pool/id" {
                  tailf:xpath-root 3;
                }
              }
            }
            leaf mapping-id {
              tailf:info
                "Associate a mapping id to this mapping";
              tailf:cli-optional-in-sequence;
              type uint32 {
                tailf:info
                  "<1-2147483647>;;Stateful NAT mapping id";
                range "1..2147483647";
              }
            }
            leaf vrf {
              tailf:info
                "Specify vrf";
              tailf:cli-optional-in-sequence;
              type string {
                tailf:info
                  "WORD;;vrf name";
              }
            }
            leaf add-route {
              tailf:info
                "Add a static route for outside local address";
              type empty;
            }
          }
          list route-map {
            tailf:info
              "Specify route-map";
            tailf:cli-suppress-mode;
            tailf:cli-delete-when-empty;
            tailf:cli-compact-syntax;
            tailf:cli-sequence-commands {
              tailf:cli-reset-siblings;
            }
            key "id";
            leaf id {
              type string {
                tailf:info
                  "WORD;;Route-map name";
              }
            }
            leaf pool {
              tailf:info
                "Name pool of local addresses";
              type string;
              tailf:non-strict-leafref {
                path "/ncs:devices/ncs:device/ncs:config/ios:ip/nat/pool/id" {
                  tailf:xpath-root 3;
                }
              }
            }
            leaf mapping-id {
              tailf:info
                "Associate a mapping id to this mapping";
              tailf:cli-optional-in-sequence;
              type uint32 {
                tailf:info
                  "<1-2147483647>;;Stateful NAT mapping id";
                range "1..2147483647";
              }
            }
            leaf vrf {
              tailf:info
                "Specify vrf";
              tailf:cli-optional-in-sequence;
              type string {
                tailf:info
                  "WORD;;vrf name";
              }
            }
            leaf add-route {
              tailf:info
                "Add a static route for outside local address";
              type empty;
            }
          }
        }
      }
      leaf-list name-server {
        tailf:info
          "Specify address of name server to use";
        tailf:cli-flat-list-syntax;
        type union {
          type inet:ipv4-address {
            tailf:info
              "A.B.C.D;;Domain server IP address (maximum of 6)";
          }
          type inet:ipv6-address {
            tailf:info
              "X:X:X:X::X;;Domain server IPv6 address (maximum of 6)";
          }
        }
      }
      container pim {
        tailf:info
          "PIM global commands";
        tailf:cli-diff-dependency "/ios:ip/vrf" {
          tailf:xpath-root 3;
        }
        tailf:cli-diff-dependency "/ios:vrf/definition" {
          tailf:xpath-root 3;
        }
        tailf:cli-diff-dependency "/ios:vrf/definition/address-family" {
          tailf:xpath-root 3;
        }
        container ssm {
          tailf:info
            "Configure Source Specific Multicast";
          leaf range {
            type union {
              type uint16 {
                tailf:info
                  "<1-99>;;Access list number";
                range "1..99";
              }
              type string {
                tailf:info
                  "WORD;;IP named access list";
                pattern '[a-zA-Z].*';
              }
            }
          }
        }
        list vrf {
          tailf:info
            "Select VPN Routing/Forwarding instance";
          tailf:cli-suppress-mode;
          tailf:cli-delete-when-empty;
          key "id";
          leaf id {
            type string {
              tailf:info
                "WORD;;VPN Routing/Forwarding instance name";
            }
          }
          container rp-address {
            tailf:info
              "PIM RP-address (Rendezvous Point)";
            tailf:cli-compact-syntax;
            tailf:cli-sequence-commands {
              tailf:cli-reset-siblings;
            }
            leaf address {
              tailf:cli-drop-node-name;
              type inet:ipv4-address {
                tailf:info
                  "A.B.C.D;;IP address of Rendezvous-point for group";
              }
            }
            leaf access-list {
              tailf:cli-drop-node-name;
              tailf:cli-optional-in-sequence;
              type union {
                type uint16 {
                  tailf:info
                    "<1-99>;;Access-list reference for group";
                  range "1..99";
                }
                type uint16 {
                  tailf:info
                    "<1300-1999>;;Access-list reference for group (expanded range)";
                  range "1300..1999";
                }
                type string {
                  tailf:info
                    "WORD;;IP Named Standard Access list";
                }
              }
            }
            leaf override {
              tailf:info
                "Overrides dynamically learnt RP mappings";
              type empty;
            }
          }
        }
      }
      container prefix-list {
        tailf:info
          "Build a prefix list";
        list prefixes {
          tailf:cli-drop-node-name;
          tailf:cli-suppress-mode;
          tailf:cli-delete-when-empty;
          tailf:cli-compact-syntax;
          key "name";
          leaf name {
            type string {
              tailf:info
                "WORD;;Name of a prefix list";
              pattern '([^s].*)|(s[^e].*)|(se[^q].*)(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            tailf:info
              "Prefix-list specific description";
            tailf:cli-multi-value;
            tailf:cli-full-command;
            type string {
              tailf:info
                "LINE;;Up to 80 characters describing this prefix-list";
              length "1..80";
            }
          }
          leaf permit {
            tailf:info
              "Specify packets to forward";
            type ios:ipv4-prefix {
              tailf:info
                "A.B.C.D  IP prefix <network>/<length>, e.g., 35.0.0.0/8";
            }
          }
          list seq {
            tailf:info
              "sequence number of an entry";
            tailf:cli-suppress-mode;
            tailf:cli-delete-when-empty;
            tailf:cli-compact-syntax;
            key "no";
            leaf no {
              type uint32 {
                range "1..4294967294";
                tailf:info
                  "<1-4294967294>;;Sequence number";
              }
              tailf:key-default "10";
            }
            container deny {
              tailf:info
                "Specify packets to reject";
              tailf:cli-sequence-commands {
                tailf:cli-reset-all-siblings;
              }
              tailf:cli-compact-syntax;
              leaf ip {
                tailf:cli-drop-node-name;
                type ios:ipv4-prefix {
                  tailf:info
                    "A.B.C.D;;IP prefix <network>/<length>, e.g., 35.0.0.0/8";
                }
              }
              leaf ge {
                tailf:info
                  "Minimum prefix length to be matched";
                tailf:cli-break-sequence-commands;
                type uint8 {
                  range "1..32";
                  tailf:info
                    "<1-32>;;Minimum prefix length";
                }
              }
              leaf le {
                tailf:info
                  "Maximum prefix length to be matched";
                tailf:cli-full-command;
                type uint8 {
                  range "1..32";
                  tailf:info
                    "<1-32>;;Maximum prefix length";
                }
              }
            }
            container permit {
              tailf:info
                "Specify packets to forward";
              tailf:cli-sequence-commands {
                tailf:cli-reset-all-siblings;
              }
              tailf:cli-compact-syntax;
              leaf ip {
                tailf:cli-drop-node-name;
                type ios:ipv4-prefix {
                  tailf:info
                    "A.B.C.D;;IP prefix <network>/<length>, e.g., 35.0.0.0/8";
                }
              }
              leaf ge {
                tailf:info
                  "Minimum prefix length to be matched";
                tailf:cli-break-sequence-commands;
                type uint8 {
                  range "1..32";
                  tailf:info
                    "<1-32>;;Minimum prefix length";
                }
              }
              leaf le {
                tailf:info
                  "Maximum prefix length to be matched";
                tailf:cli-full-command;
                type uint8 {
                  range "1..32";
                  tailf:info
                    "<1-32>;;Maximum prefix length";
                }
              }
            }
          }
        }
        leaf sequence-number {
          tailf:info
            "Include/exclude sequence numbers in NVGEN";
          tailf:cli-full-command;
          type empty;
        }
      }
      container route {
        tailf:info
          "Establish static routes";
        uses ip-route-grouping;
        leaf profile {
          tailf:info
            "Enable IP routing table profile";
          tailf:cli-full-command;
          type empty;
        }
        container static {
          tailf:info
            "Allow static routes";
          leaf adjust-time {
            tailf:info
              "Time period for adjusting static routes";
            tailf:cli-full-command;
            type uint8 {
              tailf:info
                "<1-60>;;Adjustment time in seconds";
              range "1..60";
            }
          }
          leaf inter-vrf {
            tailf:info
              "Across VRF interfaces";
            tailf:cli-full-command;
            type empty;
          }
        }
        list vrf {
          tailf:info
            "Configure static route for a VPN Routing/Forwarding instance";
          tailf:cli-suppress-mode;
          tailf:cli-delete-when-empty;
          tailf:cli-compact-syntax;
          tailf:cli-reset-container;
          tailf:cli-incomplete-command;
          tailf:cli-diff-dependency "/ios:ip/vrf" {
            tailf:xpath-root 3;
          }
          tailf:cli-diff-dependency "/ios:vrf/definition" {
            tailf:xpath-root 3;
          }
          tailf:cli-diff-dependency "/ios:vrf/definition/address-family" {
            tailf:xpath-root 3;
          }
          key "name";
          leaf name {
            type string {
              tailf:info
                "WORD;;VPN Routing/Forwarding instance name";
            }
          }
          uses ip-route-grouping;
        }
      }
      leaf routing {
        tailf:info
          "Enable IP routing";
        tailf:cli-full-command;
        type empty;
      }
      container scp {
        tailf:info
          "Scp commands";
        container server {
          tailf:info
            "Configure SCP server-side functionality";
          leaf enable {
            tailf:info
              "Enable server side of SCP";
            type empty;
          }
        }
      }
      container sla {
        tailf:info
          "IP Service Level Agreement";
        container enable {
          leaf reaction-alerts {
            type empty;
          }
        }
        leaf responder {
          type empty;
        }
      }
      container bootp {
        tailf:info
          "Config BOOTP services";
        leaf server {
          tailf:info
            "Enable BOOTP server";
          tailf:cli-boolean-no;
          tailf:cli-trim-default;
          type boolean;
          default "true";
        }
      }
      leaf source-route {
        tailf:info
          "Process packets with source routing header options";
        tailf:cli-boolean-no;
        tailf:cli-show-with-default;
        tailf:cli-full-command;
        type boolean;
        default "true";
      }
      container ssh {
        tailf:info
          "Configure ssh options";
        leaf authentication-retries {
          tailf:info
            "Specify number of authentication retries";
          type uint8 {
            tailf:info
              "<0-5>;;Number of authentication retries";
            range "0..5";
          }
        }
        leaf dscp {
          tailf:info
            "IP DSCP value for SSH traffic";
          type uint8 {
            tailf:info
              "<0-63>;;ip dscp value (default value 0 )";
            range "0..63";
          }
        }
        container logging {
          tailf:info
            "Configure logging for SSH";
          leaf events {
            tailf:info
              "Log SSH events";
            type empty;
          }
        }
        leaf precedence {
          tailf:info
            "IP Precedence value for SSH traffic";
          type uint8 {
            tailf:info
              "<0-7>;;ip precedence value (default value 0 )";
            range "0..7";
          }
        }
        leaf time-out {
          tailf:info
            "Specify SSH time-out interval";
          type uint8 {
            tailf:info
              "<1-120>;;SSH time-out interval (secs)";
            range "1..120";
          }
        }
        leaf version {
          tailf:info
            "Specify protocol version supported";
          type uint8 {
            tailf:info
              "<1-2>;;Protocol version";
            range "1..2";
          }
        }
      }
      container tacacs {
        tailf:info
          "TACACS configuration commands";
        container source-interface {
          tailf:info
            "Specify interface for source address in TACACS packets";
          tailf:cli-diff-dependency "/ios:interface" {
            tailf:xpath-root 3;
          }
          uses interface-grouping;
        }
      }
      container tcp {
        tailf:info
          "Global TCP parameters";
        container path-mtu-discovery {
          tailf:info
            "Enable path-MTU discovery on new TCP connections";
          presence "true";
          leaf age-timer {
            tailf:info
              "Set PMTU aging timer";
            type union {
              type enumeration {
                enum "infinite" {
                  tailf:info
                    "Disable pathmtu aging timer";
                }
              }
              type uint8 {
                tailf:info
                  "<10-30>;;Aging time";
                range "10..30";
              }
            }
          }
        }
      }
      container tftp {
        tailf:info
          "tftp configuration commands";
        container boot-interface {
          tailf:info
            "Force interface to use for TFTP booting";
          tailf:cli-diff-dependency "/ios:interface" {
            tailf:xpath-root 3;
          }
          uses interface-grouping;
        }
        container source-interface {
          tailf:info
            "Specify interface for source address in TFTP connections";
          tailf:cli-diff-dependency "/ios:interface" {
            tailf:xpath-root 3;
          }
          uses interface-grouping;
        }
      }
      container access-list {
        tailf:info
          "Named access list";
        tailf:cli-incomplete-command;
        tailf:cli-compact-syntax;
        container standard {
          tailf:info
            "Standard Access List";
          tailf:cli-incomplete-command;
          list std-named-acl {
            tailf:cli-drop-node-name;
            tailf:cli-full-command;
            tailf:cli-no-key-completion;
            tailf:cli-mode-name "config-std-nacl";
            key "name";
            leaf name {
              type std-acl-type;
            }
            list std-access-list-rule {
              tailf:cli-suppress-mode;
              tailf:cli-delete-when-empty;
              tailf:cli-drop-node-name;
              tailf:cli-compact-syntax;
              tailf:cli-show-long-obu-diffs;
              ordered-by user;
              key "rule";
              leaf rule {
                tailf:cli-drop-node-name;
                tailf:cli-multi-word-key;
                type string {
                  pattern '(deny.*)|(permit.*)|(remark.*)|(no.*)';
                  tailf:info
                    "deny;;Specify packets to reject
                     permit;;Specify packets to forwards
                     remark;;Access list entry comment";
                }
              }
            }
          }
        }
        container extended {
          tailf:info
            "Extended Access List";
          tailf:cli-incomplete-command;
          list ext-named-acl {
            tailf:cli-drop-node-name;
            tailf:cli-full-command;
            tailf:cli-mode-name "config-std-nacl";
            key "name";
            leaf name {
              tailf:info
                "WORD;;Access-list name";
              type string;
            }
            list ext-access-list-rule {
              tailf:cli-suppress-mode;
              tailf:cli-delete-when-empty;
              tailf:cli-drop-node-name;
              tailf:cli-compact-syntax;
              tailf:cli-show-long-obu-diffs;
              ordered-by user;
              key "rule";
              leaf rule {
                tailf:cli-drop-node-name;
                tailf:cli-multi-word-key;
                type string {
                  pattern '(permit.*)|(deny.*)|(no.*)|(remark.*)';
                  tailf:info
                    "deny;;Specify packets to reject
                     permit;;Specify packets to forwards
                     remark;;Access list entry comment";
                }
              }
            }
          }
        }
      }
    }
    container vmps {
      tailf:ncs-device-type "cli-ned";
      tailf:display-when "not(../../ncs:module) or ../../ncs:module[ncs:name='tailf-ned-cisco-ios']";
      tailf:info
        "VMPS settings";
      leaf reconfirm {
        tailf:info
          "Set VMPS reconfirm interval";
        type uint8 {
          tailf:info
            "Number of minutes between reconfirmations";
          range "0..120";
        }
      }
      leaf retry {
        tailf:info
          "Set VMPS retry count";
        type uint8 {
          tailf:info
            "<1-10>;;Retry count per server";
          range "1..10";
        }
      }
      list server {
        tailf:info
          "Configure server IP address";
        tailf:cli-suppress-mode;
        tailf:cli-delete-when-empty;
        tailf:cli-compact-syntax;
        key "name";
        leaf name {
          type host-type {
            tailf:info
              "Hostname or A.B.C.D;;IP address";
          }
        }
        leaf primary {
          tailf:info
            "Specify primary server";
          type empty;
        }
      }
    }
    container ipv6 {
      tailf:ncs-device-type "cli-ned";
      tailf:display-when "not(../../ncs:module) or ../../ncs:module[ncs:name='tailf-ned-cisco-ios']";
      tailf:info
        "Global IPv6 configuration commands";
      container access-list {
        tailf:info
          "Configure access lists";
        tailf:cli-incomplete-command;
        tailf:cli-compact-syntax;
        list named-acl {
          tailf:cli-drop-node-name;
          tailf:cli-full-command;
          tailf:cli-no-key-completion;
          tailf:cli-mode-name "config-ipv6-acl";
          key "name";
          leaf name {
            type string {
              tailf:info
                "User selected string identifying this access list";
            }
          }
          list access-list-rule {
            tailf:cli-suppress-mode;
            tailf:cli-delete-when-empty;
            tailf:cli-drop-node-name;
            tailf:cli-compact-syntax;
            tailf:cli-show-long-obu-diffs;
            ordered-by user;
            key "rule";
            leaf rule {
              tailf:cli-drop-node-name;
              tailf:cli-multi-word-key;
              type string {
                pattern '(deny.*)|(permit.*)|(remark.*)|(no.*)';
                tailf:info
                  "deny;;Specify packets to reject
                   permit;;Specify packets to forwards
                   remark;;Access list entry comment";
              }
            }
          }
        }
      }
      leaf unicast-routing {
        tailf:info
          "Enable unicast routing";
        type empty;
      }
      container multicast {
        tailf:info
          "Configure multicast related commands";
        container rpf {
          tailf:info
            "Configure multicast RPF related commands";
          container backoff {
            tailf:info
              "Backoff delay after unicast routing change";
            tailf:cli-compact-syntax;
            tailf:cli-sequence-commands {
              tailf:cli-reset-siblings;
            }
            leaf initial-delay {
              tailf:cli-drop-node-name;
              type uint16 {
                tailf:info
                  "<200-65535>;;Initial RPF backoff delay in milliseconds";
                range "200..65535";
              }
            }
            leaf max-delay {
              tailf:cli-drop-node-name;
              type uint16 {
                tailf:info
                  "<200-65535>;;Maximum RPF backoff delay in milliseconds";
                range "200..65535";
              }
            }
          }
          leaf use-bgp {
            tailf:info
              "Use BGP routes for multicast RPF lookup";
            type empty;
          }
        }
      }
      container cef {
        tailf:info
          "Cisco Express Forwarding";
        tailf:cli-delete-when-empty;
        presence "true";
        container accounting {
          tailf:info
            "Enable CEF accounting";
          leaf per-prefix {
            tailf:info
              "Enable per prefix accounting";
            type empty;
          }
          leaf prefix-length {
            tailf:info
              "Enable prefix length accounting";
            type empty;
          }
        }
        leaf distributed {
          tailf:info
            "Distributed Cisco Express Forwarding";
          tailf:cli-full-command;
          type empty;
        }
      }
      container route {
        tailf:info
          "Configure static routes";
        uses ipv6-route-grouping;
        list vrf {
          tailf:info
            "Configure static route for a VPN Routing/Forwarding instance";
          tailf:cli-suppress-mode;
          tailf:cli-delete-when-empty;
          tailf:cli-compact-syntax;
          tailf:cli-reset-container;
          tailf:cli-incomplete-command;
          tailf:cli-diff-dependency "/ios:vrf/definition" {
            tailf:xpath-root 3;
          }
          tailf:cli-diff-dependency "/ios:vrf/definition/address-family" {
            tailf:xpath-root 3;
          }
          key "name";
          leaf name {
            type string {
              tailf:info
                "WORD;VRF name";
            }
          }
          uses ipv6-route-grouping;
        }
      }
      container prefix-list {
        tailf:info
          "Build a prefix list";
        list prefixes {
          tailf:cli-drop-node-name;
          tailf:cli-suppress-mode;
          tailf:cli-delete-when-empty;
          key "name";
          leaf name {
            type string {
              tailf:info
                "WORD;;Name of a prefix list";
              pattern '([^s].*)|(s[^e].*)|(se[^q].*)(seq[^u].*)|(sequ[^e].*)|(seque[^n].*)|(sequen[^c].*)|(sequenc[^e].*)|(sequence[^\-].*)|(sequence\-[^n].*)|(sequence\-n[^u].*)|(sequence\-nu[^m].*)|(sequence\-num[^b].*)|(sequence\-numb[^e].*)|(sequence\-numbe[^r].*)|(sequence\-number..*)';
            }
          }
          leaf description {
            tailf:info
              "Prefix-list specific description";
            tailf:cli-multi-value;
            tailf:cli-full-command;
            type string {
              length "1..80";
              tailf:info
                "LINE;;Up to 80 characters describing this prefix-list";
            }
          }
          leaf permit {
            tailf:info
              "Specify packets to forward";
            type ios:ipv6-prefix {
              tailf:info
                "X:X:X:X::X/<0-128>  IPv6 prefix<network>/<length>";
            }
          }
          list seq {
            tailf:info
              "sequence number of an entry";
            tailf:cli-suppress-mode;
            tailf:cli-delete-when-empty;
            key "no";
            leaf no {
              type uint32 {
                range "1..4294967294";
                tailf:info
                  "<1-4294967294>;;Sequence number";
              }
              tailf:key-default "10";
            }
            container deny {
              tailf:info
                "Specify packets to reject";
              tailf:cli-sequence-commands {
                tailf:cli-reset-all-siblings;
              }
              tailf:cli-compact-syntax;
              leaf ip {
                tailf:cli-drop-node-name;
                type ios:ipv6-prefix {
                  tailf:info
                    "X:X:X:X::X/<0-128>  IPv6 prefix<network>/<length>";
                }
              }
              leaf ge {
                tailf:info
                  "Minimum prefix length to be matched";
                tailf:cli-break-sequence-commands;
                type uint16 {
                  range "1..128";
                  tailf:info
                    "<1-128>;;Minimum prefix length";
                }
              }
              leaf le {
                tailf:info
                  "Maximum prefix length to be matched";
                tailf:cli-full-command;
                type uint16 {
                  range "1..128";
                  tailf:info
                    "<1-128>;;Maximum prefix length";
                }
              }
            }
            container permit {
              tailf:info
                "Specify packets to forward";
              tailf:cli-sequence-commands {
                tailf:cli-reset-all-siblings;
              }
              tailf:cli-compact-syntax;
              leaf ip {
                tailf:cli-drop-node-name;
                type ios:ipv6-prefix {
                  tailf:info
                    "X:X:X:X::X/<0-128>  IPv6 prefix<network>/<length>";
                }
              }
              leaf ge {
                tailf:info
                  "Minimum prefix length to be matched";
                tailf:cli-break-sequence-commands;
                type uint16 {
                  range "1..128";
                  tailf:info
                    "<1-128>;;Minimum prefix length";
                }
              }
              leaf le {
                tailf:info
                  "Maximum prefix length to be matched";
                tailf:cli-full-command;
                type uint16 {
                  range "1..128";
                  tailf:info
                    "<1-128>;;Maximum prefix length";
                }
              }
            }
          }
        }
        leaf sequence-number {
          tailf:info
            "Include/exclude sequence numbers in NVGEN";
          tailf:cli-full-command;
          type empty;
        }
      }
    }
    container vlan {
      tailf:ncs-device-type "cli-ned";
      tailf:display-when "not(../../ncs:module) or ../../ncs:module[ncs:name='tailf-ned-cisco-ios']";
      tailf:info
        "VLAN commands";
      container accounting {
        tailf:info
          "VLAN accounting configuration";
      }
      container internal {
        tailf:info
          "internal VLAN";
        container allocation {
          tailf:info
            "internal VLAN allocation";
          leaf policy {
            type enumeration {
              enum "ascending" {
                tailf:info
                  "Allocates internal VLANs from 1006 to 4094";
              }
              enum "descending" {
                tailf:info
                  "Allocates internal VLANs from 4094 to 1006.";
              }
            }
          }
        }
      }
      container dot1q {
        tailf:info
          "dot1q parameters";
        container tag {
          tailf:info
            "tag parameters";
          leaf native {
            tailf:info
              "tag native vlan";
            type empty;
          }
        }
      }
      container access-log {
        tailf:info
          "Configure VACL logging";
        leaf maxflow {
          tailf:info
            "Set vacl logging maximum flow number";
          type uint16 {
            tailf:info
              "<0-2048>;;Maximum flow number";
            range "0..2048";
          }
        }
        leaf ratelimit {
          tailf:info
            "Set vacl logging rate limiter";
          type uint16 {
            tailf:info
              "<10-5000>;;Maximum number of packets logged per second";
            range "10..5000";
          }
        }
        leaf threshold {
          tailf:info
            "Set vacl log-update threshold";
          type uint32 {
            tailf:info
              "<0-2147483647>;;log-update threshold (number of hits)";
            range "0..2147483647";
          }
        }
      }
      list vlan-list {
        tailf:cli-drop-node-name;
        tailf:cli-mode-name "config-vlan";
        tailf:cli-range-list-syntax;
        key "id";
        leaf id {
          type uint16 {
            range "1..4094";
            tailf:info
              "<1-3967,4048-4094>;;VLAN ID 1-4094 or range(s): 1-5, 10 or 2-5,7-19";
          }
        }
        leaf name {
          tailf:info
            "Ascii name of the VLAN";
          tailf:cli-full-command;
          tailf:cli-multi-value;
          type string {
            length "1..32";
            tailf:info
              "The ascii name for the VLAN (Max Size 32)";
          }
        }
        leaf uni-vlan {
          tailf:info
            "Configure a UNI VLAN";
          tailf:cli-full-command;
          type enumeration {
            enum "community" {
              tailf:info
                "UNI/ENI community VLAN";
            }
            enum "isolated" {
              tailf:info
                "UNI/ENI isolated VLAN";
            }
          }
        }
      }
    }
    container interface {
      tailf:ncs-device-type "cli-ned";
      tailf:display-when "not(../../ncs:module) or ../../ncs:module[ncs:name='tailf-ned-cisco-ios']";
      tailf:info
        "Configure interfaces";
      tailf:cli-diff-dependency "/ios:vrf" {
        tailf:xpath-root 3;
      }
      tailf:cli-explicit-exit;
      list Embedded-Service-Engine {
        tailf:info
          "cisco embedded service engine module";
        tailf:cli-allow-join-with-key {
          tailf:cli-display-joined;
        }
        tailf:cli-mode-name "config-if";
        key "name";
        leaf name {
          type string {
            tailf:info
              "<0-2>/<0-0>;;Embedded-Service-Engine interface number";
          }
        }
        uses interface-common-grouping;
      }
      list FastEthernet {
        tailf:info
          "FastEthernet IEEE 802.3";
        tailf:cli-allow-join-with-key {
          tailf:cli-display-joined;
        }
        tailf:cli-mode-name "config-if";
        key "name";
        leaf name {
          type string {
            tailf:info
              "<0-66>/<0-128>;;FastEthernet interface number";
          }
        }
        uses interface-ethernet-grouping;
        uses interface-common-grouping;
        uses interface-zone-member-grouping;
        uses interface-switch-grouping;
      }
      list GigabitEthernet {
        tailf:info
          "GigabitEthernet IEEE 802.3z";
        tailf:cli-allow-join-with-key {
          tailf:cli-display-joined;
        }
        tailf:cli-mode-name "config-if";
        key "name";
        leaf name {
          type string {
            tailf:info
              "<0-66>/<0-128>;;GigabitEthernet interface number";
          }
        }
        leaf media-type {
          tailf:info
            "Media type";
          type enumeration {
            enum "rj45" {
              tailf:info
                "Copper";
            }
            enum "sfp" {
              tailf:info
                "Fiber";
            }
          }
        }
        leaf port-type {
          type enumeration {
            enum "nni";
          }
        }
        uses interface-ethernet-grouping;
        uses interface-common-grouping;
        uses interface-zone-member-grouping;
        uses interface-switch-grouping;
      }
      list TenGigabitEthernet {
        tailf:info
          "Ten Gigabit Ethernet";
        tailf:cli-allow-join-with-key {
          tailf:cli-display-joined;
        }
        tailf:cli-mode-name "config-if";
        key "name";
        leaf name {
          type string {
            tailf:info
              "<0-66>/<0-128>;;TenGigabitEthernet interface number";
          }
        }
        leaf media-type {
          tailf:info
            "Media type";
          type enumeration {
            enum "rj45" {
              tailf:info
                "Copper";
            }
            enum "sfp" {
              tailf:info
                "Fiber";
            }
          }
        }
        leaf port-type {
          type enumeration {
            enum "nni";
          }
        }
        uses interface-ethernet-grouping;
        uses interface-common-grouping;
        uses interface-zone-member-grouping;
        uses interface-switch-grouping;
      }
      list Loopback {
        tailf:info
          "Loopback interface";
        tailf:cli-allow-join-with-key {
          tailf:cli-display-joined;
        }
        tailf:cli-mode-name "config-if";
        key "name";
        leaf name {
          type string {
            tailf:info
              "<0-2147483647>;;Loopback interface number";
          }
        }
        uses interface-common-grouping;
      }
      list Port-channel {
        tailf:info
          "Ethernet Channel of interfaces";
        tailf:cli-allow-join-with-key {
          tailf:cli-display-joined;
        }
        tailf:cli-mode-name "config-if";
        key "name";
        leaf name {
          type uint32 {
            tailf:info
              "<1-512>;;Port-channel interface number";
            range "1..512";
          }
        }
        leaf speed {
          tailf:info
            "Configure speed operation.";
          type enumeration {
            enum "10" {
              tailf:info
                "Force 10 Mbps operation";
            }
            enum "100" {
              tailf:info
                "Force 100 Mbps operation";
            }
            enum "1000" {
              tailf:info
                "Enable AUTO speed configuration";
            }
            enum "nonegotiate";
            enum "auto" {
              tailf:info
                "Enable AUTO speed configuration";
            }
          }
        }
        uses interface-common-grouping;
        uses interface-switch-grouping;
      }
      list Vlan {
        tailf:info
          "Catalyst Vlans";
        tailf:cli-allow-join-with-key {
          tailf:cli-display-joined;
        }
        key "name";
        leaf name {
          type uint16 {
            tailf:info
              "<1-4094>;;Vlan interface number";
            range "1..4094";
          }
        }
        uses interface-common-grouping;
        uses interface-zone-member-grouping;
      }
      list Group-Async {
        tailf:info
          "Async Group interface";
        tailf:cli-allow-join-with-key {
          tailf:cli-display-joined;
        }
        key "name";
        leaf name {
          type uint16 {
            tailf:info
              "<0-64>;;Group-Async interface number";
            range "0..64";
          }
        }
        leaf physical-layer {
          tailf:info
            "Configure sync or async physical layer on serial interface";
          type enumeration {
            enum "async" {
              tailf:info
                "Configure asynchronous physical layer on serial interface";
            }
            enum "sync" {
              tailf:info
                "Configure synchronous physical layer on serial interface";
            }
          }
        }
        uses interface-common-grouping;
      }
      list Multilink {
        tailf:info
          "Multilink-group interface";
        tailf:cli-allow-join-with-key {
          tailf:cli-display-joined;
        }
        tailf:cli-mode-name "config-if";
        tailf:cli-full-command;
        key "name";
        leaf name {
          type uint16 {
            tailf:info
              "<1-65535>;;Multilink interface number";
            range "1..65535";
          }
        }
        uses interface-common-grouping;
        uses interface-pointtopoint-grouping;
      }
      list Serial {
        tailf:info
          "Serial interface";
        tailf:cli-allow-join-with-key {
          tailf:cli-display-joined;
        }
        tailf:cli-mode-name "config-if";
        tailf:cli-full-command;
        key "name";
        leaf name {
          type string;
        }
        uses interface-common-grouping;
        uses interface-pointtopoint-grouping;
      }
      list Virtual-Template {
        tailf:info
          "Virtual Template interface";
        tailf:cli-allow-join-with-key {
          tailf:cli-display-joined;
        }
        tailf:cli-mode-name "config-if";
        tailf:cli-full-command;
        tailf:cli-explicit-exit;
        key "name";
        leaf name {
          type uint16 {
            tailf:info
              "<1-4095>;;Virtual-Template interface number";
            range "1..4095";
          }
        }
        uses interface-ethernet-grouping;
        uses interface-common-grouping;
        uses interface-zone-member-grouping;
        uses interface-switch-grouping;
        uses interface-pointtopoint-grouping;
      }
    }
    list route-map {
      tailf:ncs-device-type "cli-ned";
      tailf:display-when "not(../ncs:module) or ../ncs:module[ncs:name='tailf-ned-cisco-ios']";
      tailf:info
        "Route map tag";
      tailf:cli-mode-name "config-route-map";
      tailf:cli-compact-syntax;
      tailf:cli-full-command;
      key "name sequence";
      leaf name {
        tailf:info
          "WORD;;Route map tag";
        type string;
      }
      leaf sequence {
        tailf:cli-drop-node-name;
        type uint16 {
          tailf:info
            "<0-65535>;;Sequence to insert to/delete from existing route-map entry";
          range "0..65535";
        }
      }
      leaf operation {
        tailf:cli-drop-node-name;
        tailf:cli-prefix-key {
          tailf:cli-before-key 2;
        }
        type enumeration {
          enum "deny" {
            tailf:code-name "op_deny";
            tailf:info
              "Route map denies set operations";
          }
          enum "permit" {
            tailf:code-name "op_internet";
            tailf:info
              "Route map permits set operations";
          }
        }
        default "permit";
      }
      container set {
        tailf:info
          "Set values in destination routing protocol";
        container as-path {
          tailf:info
            "Prepend string for a BGP AS-path attribute";
          container prepend {
            tailf:info
              "Prepend to the as-path";
            container as-container {
              tailf:cli-drop-node-name;
              leaf as-number {
                tailf:info
                  "<1-65535>;;AS number";
                tailf:cli-drop-node-name;
                tailf:cli-multi-value;
                type string {
                  tailf:info
                    "<1-65535>;;AS number";
                }
              }
            }
            container last-as-cont {
              tailf:cli-drop-node-name;
              leaf last-as {
                type uint16 {
                  tailf:info
                    "<1..10>;;number of last-AS prepends";
                  range "1..10";
                }
              }
            }
          }
          container tag {
            tailf:info
              "Set the tag as an AS-path attribute";
            tailf:cli-full-command;
            presence "tag";
          }
        }
        container community {
          tailf:info
            "BGP community attribute";
          choice community-choice {
            case community-numberi-case {
              leaf community-number {
                tailf:cli-drop-node-name;
                type uint32 {
                  tailf:info
                    "<1-4294967295>;;community number";
                  range "1..4294967295";
                }
              }
              leaf community-number-alt-format {
                tailf:cli-drop-node-name;
                type string {
                  tailf:info
                    "aa:nn;;community number in aa:nn format";
                  pattern '(\d+:\d+)';
                }
              }
            }
            case well-known-community-case {
              leaf well-known-communities {
                tailf:cli-drop-node-name;
                type enumeration {
                  enum "internet" {
                    tailf:info
                      "Internet (well-known community)";
                  }
                  enum "local-AS" {
                    tailf:info
                      "Do not send outside local AS (well-known community)";
                  }
                  enum "no-advertise" {
                    tailf:info
                      "Do not advertise to any peer (well-known community)";
                  }
                  enum "no-export" {
                    tailf:info
                      "Do not export to next AS (well-known community)";
                  }
                  enum "none" {
                    tailf:info
                      "No community attribute";
                  }
                }
              }
            }
          }
          leaf additive {
            tailf:info
              "Add to the existing community";
            type empty;
          }
        }
        container comm-list {
          tailf:info
            "set BGP community list (for deletion)";
          tailf:cli-sequence-commands;
          choice comm-list-choice {
            leaf comm-list-standard {
              tailf:cli-drop-node-name;
              tailf:cli-incomplete-command;
              type uint16 {
                tailf:info
                  "<1-99>;;Community-list number (standard)";
                range "1..99";
              }
            }
            leaf comm-list-expanded {
              tailf:cli-drop-node-name;
              tailf:cli-incomplete-command;
              type uint16 {
                tailf:info
                  "<100-500>;;Community-list number (expanded)";
                range "100..500";
              }
            }
            leaf comm-list-name {
              tailf:cli-drop-node-name;
              tailf:cli-incomplete-command;
              type string {
                tailf:info
                  "WORD;;Community-list name";
              }
            }
          }
          leaf delete {
            tailf:cli-full-command;
            tailf:info
              "Delete matching communities";
            type empty;
          }
        }
        container extcommunity {
          tailf:info
            "BGP extended community attribute";
          leaf-list rt {
            tailf:info
              "Route Target extended community";
            tailf:cli-flat-list-syntax;
            type asn-ip-type {
              tailf:info
                "ASN:nn or IP-address:nn;;VPN extended community";
            }
          }
        }
        container ip {
          tailf:info
            "IP specific information";
          container next-hop {
            tailf:info
              "Next hop address";
            choice next-hop-choice {
              leaf-list address {
                tailf:cli-drop-node-name;
                tailf:cli-flat-list-syntax;
                type inet:ipv4-address {
                  tailf:info
                    "A.B.C.D;;IP address of next hop";
                }
              }
              container dynamic {
                tailf:info
                  "application dynamically sets next hop";
                leaf dhcp {
                  tailf:info
                    "DHCP learned next hop";
                  type empty;
                }
              }
              leaf peer-address {
                tailf:info
                  "Use peer address (for BGP only)";
                type empty;
              }
            }
          }
        }
        leaf metric {
          tailf:info
            "Metric value for destination routing protocol";
          type string {
            tailf:info
              "+/-<metric>;;Add or subtract metric
               <0-4294967295>;;Metric value or Bandwidth in Kbits per second";
            pattern '[+-]?[0-9].*';
          }
        }
        leaf metric-type {
          tailf:info
            "Type of metric for destination routing protocol";
          type enumeration {
            enum "external" {
              tailf:info
                "IS-IS external metric";
            }
            enum "internal" {
              tailf:info
                "IS-IS internal metric or Use IGP metric as the MED for BGP";
            }
            enum "type-1" {
              tailf:info
                "OSPF external type 1 metric";
            }
            enum "type-2" {
              tailf:info
                "OSPF external type 2 metric";
            }
          }
        }
        leaf weight {
          tailf:info
            "BGP weight for routing table";
          type uint32 {
            tailf:info
              "<0-65535>;;Weight value";
            range "0..65535";
          }
        }
        container origin {
          tailf:info
            "BGP origin code";
          choice origin-choice {
            leaf origin-value {
              tailf:cli-drop-node-name;
              type enumeration {
                enum "igp" {
                  tailf:info
                    "local IGP";
                }
                enum "incomplete" {
                  tailf:info
                    "unknown heritage";
                }
              }
            }
            leaf egp {
              tailf:info
                "remote EGP";
              type uint32 {
                tailf:info
                  "<0-65535>;;remote AS";
                range "0..65535";
              }
            }
          }
        }
      }
      container match {
        tailf:info
          "Match values from routing table";
        container community {
          tailf:info
            "Match BGP community list";
          leaf-list name {
            tailf:info
              "Named Access List";
            tailf:cli-drop-node-name;
            tailf:cli-flat-list-syntax;
            type string {
              tailf:info
                "<1-99>       Community-list number (standard)
                 <100-500>       Community-list number (expanded)
                 WORD            Community-list name
                 exact-match     Do exact matching of communities
                ";
            }
          }
        }
        container ip {
          tailf:info
            "IP specific information";
          container address {
            tailf:info
              "Match address of route or match packet";
            choice address-choice {
              leaf access-list {
                tailf:cli-drop-node-name;
                type exp-acl-type;
              }
              leaf prefix-list {
                tailf:info
                  "Match entries of prefix-lists";
                type string;
                tailf:non-strict-leafref {
                  path "/ncs:devices/ncs:device/ncs:config/ios:ip/prefix-list/prefixes/name" {
                    tailf:xpath-root 3;
                  }
                }
              }
            }
          }
        }
        container ipv6 {
          tailf:info
            "IPv6 specific information";
          container address {
            tailf:info
              "Match address of route";
            choice address-choice {
              leaf access-list {
                tailf:cli-drop-node-name;
                type string {
                  tailf:info
                    "WORD;;IPv6 access-list name";
                  pattern '[a-zA-Z].*';
                }
              }
              leaf prefix-list {
                tailf:info
                  "IPv6 prefix-list";
                type string;
                tailf:non-strict-leafref {
                  path "/ncs:devices/ncs:device/ncs:config/ios:ipv6/prefix-list/prefixes/name" {
                    tailf:xpath-root 3;
                  }
                }
              }
            }
          }
        }
      }
    }
    container authentication {
      tailf:ncs-device-type "cli-ned";
      tailf:display-when "not(../../ncs:module) or ../../ncs:module[ncs:name='tailf-ned-cisco-ios']";
      container mac-move {
        leaf permit {
          type empty;
        }
      }
    }
    container banner {
      tailf:ncs-device-type "cli-ned";
      tailf:display-when "not(../../ncs:module) or ../../ncs:module[ncs:name='tailf-ned-cisco-ios']";
      tailf:info
        "Define a login banner";
      container exec {
        tailf:info
          "Set EXEC process creation banner";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must '../end-marker = ../start-marker' {
            tailf:xpath-root 3;
            tailf:dependency "../start-marker";
          }
        }
      }
      container login {
        tailf:info
          "Set login banner";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must '../end-marker = ../start-marker' {
            tailf:xpath-root 3;
            tailf:dependency "../start-marker";
          }
        }
      }
      container prompt-timeout {
        tailf:info
          "Set Message for login authentication timeout";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must '../end-marker = ../start-marker' {
            tailf:xpath-root 3;
            tailf:dependency "../start-marker";
          }
        }
      }
      container motd {
        tailf:info
          "Set Message of the Day banner";
        tailf:cli-sequence-commands {
          tailf:cli-reset-siblings;
        }
        tailf:cli-compact-syntax;
        leaf start-marker {
          tailf:cli-drop-node-name;
          type string;
        }
        leaf message {
          tailf:cli-drop-node-name;
          type string;
        }
        leaf end-marker {
          tailf:cli-drop-node-name;
          type string;
          must '../end-marker = ../start-marker' {
            tailf:xpath-root 3;
            tailf:dependency "../start-marker";
          }
        }
      }
    }
    list table-map {
      tailf:ncs-device-type "cli-ned";
      tailf:display-when "not(../ncs:module) or ../ncs:module[ncs:name='tailf-ned-cisco-ios']";
      tailf:info
        "Configure Table Map";
      tailf:cli-mode-name "config-tablemap";
      key "name";
      leaf name {
        type string {
          tailf:info
            "WORD;;table-map name";
        }
      }
      leaf default {
        tailf:info
          "the default behavior for setting value not found in the table map";
        type union {
          type uint8 {
            tailf:info
              "tablemap default value";
            range "0..63";
          }
          type enumeration {
            enum "copy" {
              tailf:info
                "set the default behavior for value not found in the table map to copy";
            }
            enum "ignore" {
              tailf:info
                "set the default behavior for value not found in the table map to ignore";
            }
          }
        }
      }
      list map {
        tailf:info
          "map to_value from from_value";
        tailf:cli-compact-syntax;
        tailf:cli-reset-container;
        tailf:cli-suppress-mode;
        tailf:cli-delete-when-empty;
        key "from to";
        leaf from {
          tailf:info
            "map from value";
          tailf:cli-expose-key-name;
          type uint8 {
            tailf:info
              "<0-63>;;tablemap from value";
            range "0..63";
          }
        }
        leaf to {
          tailf:info
            "map to value";
          tailf:cli-expose-key-name;
          type uint8 {
            tailf:info
              "<0-63>;;tablemap to value";
            range "0..63";
          }
        }
      }
    }
    container mls {
      tailf:ncs-device-type "cli-ned";
      tailf:display-when "not(../../ncs:module) or ../../ncs:module[ncs:name='tailf-ned-cisco-ios']";
      tailf:info
        "mls global commands";
      tailf:cli-incomplete-no;
      container acl {
        tailf:info
          "MLS ACL operation";
        container tcam {
          tailf:info
            "ACL TCAM";
          leaf default-result {
            tailf:info
              "Default result to be used during tcam programming";
            type enumeration {
              enum "bridge" {
                tailf:info
                  "Bridge result";
              }
              enum "deny" {
                tailf:info
                  "Deny result";
              }
              enum "permit" {
                tailf:info
                  "Permit result";
              }
            }
          }
          container log-update {
            tailf:info
              "Log TCAM updates";
            presence "true";
            leaf rate-limit-msg {
              tailf:info
                "Enable/Disable syslog ratelimiting";
              type enumeration {
                enum "disable" {
                  tailf:info
                    "Disable ratelimiting syslog";
                }
                enum "enable" {
                  tailf:info
                    "Enable syslog ratelimiting at 1 per second";
                }
              }
            }
          }
          leaf share-global {
            tailf:info
              "share global deny or permit any entries";
            tailf:cli-boolean-no;
            tailf:cli-trim-default;
            type boolean;
            default "true";
          }
        }
      }
      container cef {
        tailf:info
          "cef keyword";
        container error {
          leaf action {
            type enumeration {
              enum "reset";
            }
          }
        }
      }
      container flow {
        tailf:info
          "flowmask keyword";
        leaf ip {
          tailf:info
            "flowmask ip keyword";
          type enumeration {
            enum "interface-destination" {
              tailf:info
                "interface-destination flow keyword";
            }
            enum "interface-destination-source" {
              tailf:info
                "interface-destination-source flow keyword";
            }
            enum "interface-full" {
              tailf:info
                "interface-full flow keyword";
            }
            enum "interface-source" {
              tailf:info
                "interface-source only flow keyword";
            }
          }
        }
      }
      container ip {
        tailf:info
          "ip keyword";
        container multicast {
          tailf:info
            "multicast keyword";
          tailf:cli-display-separated;
          presence "true";
          container consistency-check {
            tailf:info
              "Set consistency checking characteristics";
            presence "true";
            leaf settle-time {
              tailf:info
                "Settle time for entry/oif for consistancy-checker";
              type uint16 {
                tailf:info
                  "<2-3600>;;Settle time for entry/oif in seconds";
                range "2..3600";
              }
            }
          }
          leaf flow-stat-timer {
            tailf:info
              "timer for flow statistic used by mls-msc and mlsm";
            type uint8 {
              tailf:info
                "<1-100>;;#seconds between one batch and another";
              range "1..100";
            }
          }
        }
      }
      container mls-qos-conf {
        tailf:cli-no-keyword;
        tailf:cli-drop-node-name;
        leaf qos {
          type empty;
        }
      }
      container qos {
        tailf:info
          "QoS parameters";
        tailf:cli-incomplete-command;
        tailf:cli-incomplete-no;
        list aggregate-policer {
          tailf:info
            "Assign aggregate policer";
          tailf:cli-suppress-mode;
          tailf:cli-delete-when-empty;
          tailf:cli-compact-syntax;
          tailf:cli-sequence-commands {
            tailf:cli-reset-all-siblings;
          }
          key "name";
          leaf name {
            type string {
              tailf:info
                "WORD;;aggregate policer name";
            }
          }
          leaf target-bit-rate {
            tailf:cli-drop-node-name;
            type uint64 {
              tailf:info
                "<32000-60000000000>;;Target Bit Rate (bits per second) (postfix k, m, g optional; decimal point allowed)";
              range "32000..60000000000";
            }
          }
          leaf burst-normal {
            tailf:cli-drop-node-name;
            tailf:cli-optional-in-sequence;
            type uint32 {
              tailf:info
                "<1000-31250000>;;Normal burst bytes";
              range "1000..31250000";
            }
          }
          leaf burst-max {
            tailf:cli-drop-node-name;
            tailf:cli-optional-in-sequence;
            when '../burst-normal' {
              tailf:xpath-root 3;
              tailf:dependency "../burst-normal";
            }
            type uint32 {
              tailf:info
                "<1000-31250000>;;Maximum burst bytes";
              range "1000..31250000";
            }
          }
          leaf pir {
            tailf:info
              "PIR";
            tailf:cli-optional-in-sequence;
            type uint64 {
              tailf:info
                "<32000-60000000000>;;Target Bit Rate (bits per second) (postfix k, m, g optional; decimal point allowed)";
              range "32000..60000000000";
            }
          }
          container conform-action {
            tailf:info
              "action when rate is not exceeded";
            tailf:cli-optional-in-sequence;
            tailf:cli-compact-syntax;
            tailf:cli-flatten-container;
            choice action-choice {
              leaf drop {
                tailf:info
                  "drop packet";
                type empty;
              }
              leaf set-dscp-transmit {
                tailf:info
                  "set dscp and send it";
                type dscp-type;
              }
              leaf set-mpls-exp-imposition-transmit {
                tailf:info
                  "set exp at tag imposition and send it";
                type uint8 {
                  tailf:info
                    "<0-7>;;new exp";
                  range "0..7";
                }
              }
              leaf set-prec-transmit {
                tailf:info
                  "rewrite packet precedence and send it";
                type uint8 {
                  tailf:info
                    "<0-7>;;new precedence";
                  range "0..7";
                }
              }
              leaf transmit {
                tailf:info
                  "transmit packet";
                type empty;
              }
            }
          }
          leaf exceed-action {
            tailf:info
              "action when rate is exceeded";
            tailf:cli-optional-in-sequence;
            type enumeration {
              enum "drop" {
                tailf:info
                  "drop packet";
              }
              enum "policed-dscp-transmit" {
                tailf:info
                  "change dscp per policed-dscp map and send it";
              }
              enum "transmit" {
                tailf:info
                  "transmit packet";
              }
            }
          }
          leaf violate-action {
            tailf:info
              "action when rate violated";
            type enumeration {
              enum "drop" {
                tailf:info
                  "drop packet";
              }
              enum "policed-dscp-transmit" {
                tailf:info
                  "change dscp per policed-dscp map and send it";
              }
              enum "transmit" {
                tailf:info
                  "transmit packet";
              }
            }
          }
        }
        container rewrite {
          tailf:info
            "packet qos rewrite enable/disable";
          container ip {
            tailf:info
              "ip packet qos rewrite enable/disable";
            container dscp {
              tailf:info
                "packet ip dscp rewrite enable/disable";
              presence "true";
              leaf slot {
                tailf:info
                  "slot number";
                type string {
                  tailf:info
                    "WORD;;Slots seperated by commas. Valid slots: 1,2,3,4,5,6,7,8,9";
                }
              }
            }
          }
        }
      }
      container rate-limit {
        tailf:info
          "Rate limit different behaviors";
        container layer2 {
          tailf:info
            "layer2 protocol cases";
          container l2pt {
            tailf:cli-compact-syntax;
            tailf:cli-sequence-commands {
              tailf:cli-reset-siblings;
            }
            tailf:info
              "layer2 protocol tunnelling packets";
            leaf packets-per-second {
              tailf:cli-drop-node-name;
              type uint32 {
                tailf:info
                  "<10-1000000>;;packets per second";
                range "10..1000000";
              }
            }
            leaf packets-in-burst {
              tailf:cli-drop-node-name;
              type uint32 {
                tailf:info
                  "<1-255>;;packets in burst";
                range "1..255";
              }
            }
          }
          container pdu {
            tailf:info
              "layer2 protocol data unit packets";
            tailf:cli-compact-syntax;
            tailf:cli-sequence-commands {
              tailf:cli-reset-siblings;
            }
            leaf packets-per-second {
              tailf:cli-drop-node-name;
              type uint32 {
                tailf:info
                  "<10-1000000>;;packets per second";
                range "10..1000000";
              }
            }
            leaf packets-in-burst {
              tailf:cli-drop-node-name;
              type uint32 {
                tailf:info
                  "<1-255>;;packets in burst";
                range "1..255";
              }
            }
          }
        }
      }
      container verify {
        tailf:info
          "enable hardware packet parsing error checks";
        container ip {
          tailf:info
            "check on IP packets";
          leaf checksum {
            tailf:info
              "check for packet checksum errors";
            tailf:cli-boolean-no;
            tailf:cli-trim-default;
            type boolean;
            default "true";
          }
          container length {
            tailf:info
              "check for packet length errors";
            leaf consistent {
              tailf:info
                "check length in header against physical frame length";
              tailf:cli-boolean-no;
              tailf:cli-trim-default;
              type boolean;
              default "true";
            }
            leaf minimum {
              tailf:info
                "check for minimum packet length";
              tailf:cli-boolean-no;
              tailf:cli-trim-default;
              type boolean;
              default "true";
            }
          }
          leaf same-address {
            tailf:info
              "check for packet having equal source and destination IP addresses";
            type empty;
          }
          leaf syslog {
            tailf:info
              "syslog packet parse errors";
            type empty;
          }
        }
      }
    }
    container policer {
      tailf:ncs-device-type "cli-ned";
      tailf:display-when "not(../../ncs:module) or ../../ncs:module[ncs:name='tailf-ned-cisco-ios']";
      tailf:info
        "Switch policer";
      list aggregate {
        tailf:info
          "Named aggregate policer";
        tailf:cli-suppress-mode;
        tailf:cli-delete-when-empty;
        tailf:cli-compact-syntax;
        tailf:cli-reset-container;
        tailf:cli-sequence-commands {
          tailf:cli-reset-siblings;
        }
        key "name";
        leaf name {
          type string {
            tailf:info
              "WORD;;aggregate policer Name";
          }
        }
        leaf cir {
          tailf:info
            "Committed information rate";
          type uint32 {
            tailf:info
              "<8000-1000000000>;;Bits per second";
            range "8000..1000000000";
          }
        }
        leaf bc {
          tailf:info
            "Conform burst";
          tailf:cli-optional-in-sequence;
          type uint32 {
            tailf:info
              "<8000-1000000000>;;Burst bytes";
            range "8000..1000000000";
          }
        }
        leaf conform-action {
          tailf:info
            "action when rate is within conform and conform + exceed burst";
          tailf:cli-optional-in-sequence;
          type empty;
        }
        leaf set-qos-transmit {
          tailf:info
            "set qos-group and send it";
          when '../conform-action' {
            tailf:xpath-root 3;
          }
          tailf:cli-optional-in-sequence;
          type uint8 {
            tailf:info
              "<0-99>;;new qos-group";
            range "0..99";
          }
        }
        leaf set-dot1ad-dei-transmit {
          tailf:info
            "set dei and send it";
          when '../conform-action' {
            tailf:xpath-root 3;
          }
          tailf:cli-optional-in-sequence;
          type uint8 {
            tailf:info
              "<0-1>;;new dei value";
            range "0..1";
          }
        }
        leaf set-prec-transmit {
          tailf:info
            "rewrite packet precedence and send it";
          when '../conform-action' {
            tailf:xpath-root 3;
          }
          tailf:cli-optional-in-sequence;
          type prec_value-type;
        }
        container set-prec-transmit-table {
          when '../set-prec-transmit' {
            tailf:xpath-root 3;
          }
          tailf:cli-no-keyword;
          tailf:cli-drop-node-name;
          tailf:cli-optional-in-sequence;
          tailf:cli-flatten-container;
          leaf table {
            tailf:info
              "Set packet cos from cos based on table map";
            tailf:cli-optional-in-sequence;
            type string;
            tailf:non-strict-leafref {
              path "/ncs:devices/ncs:device/ncs:config/ios:table-map/name" {
                tailf:xpath-root 3;
              }
            }
          }
        }
        leaf set-dscp-transmit {
          tailf:info
            "set dscp and send it";
          when '../conform-action' {
            tailf:xpath-root 3;
          }
          tailf:cli-optional-in-sequence;
          type dscp-type;
        }
        container set-dscp-transmit-table {
          when '../set-dscp-transmit' {
            tailf:xpath-root 3;
          }
          tailf:cli-no-keyword;
          tailf:cli-drop-node-name;
          tailf:cli-optional-in-sequence;
          tailf:cli-flatten-container;
          leaf table {
            tailf:info
              "Set packet cos from cos based on table map";
            tailf:cli-optional-in-sequence;
            type string;
            tailf:non-strict-leafref {
              path "/ncs:devices/ncs:device/ncs:config/ios:table-map/name" {
                tailf:xpath-root 3;
              }
            }
          }
        }
        leaf set-cos-transmit {
          tailf:info
            "set cos and send it";
          when '../conform-action' {
            tailf:xpath-root 3;
          }
          tailf:cli-optional-in-sequence;
          type cos_value-type;
        }
        container set-cos-transmit-table {
          when '../set-cos-transmit' {
            tailf:xpath-root 3;
          }
          tailf:cli-no-keyword;
          tailf:cli-drop-node-name;
          tailf:cli-optional-in-sequence;
          tailf:cli-flatten-container;
          leaf table {
            tailf:info
              "Set packet cos from cos based on table map";
            tailf:cli-optional-in-sequence;
            type string;
            tailf:non-strict-leafref {
              path "/ncs:devices/ncs:device/ncs:config/ios:table-map/name" {
                tailf:xpath-root 3;
              }
            }
          }
        }
        leaf transmit {
          tailf:info
            "transmit packet";
          when '../conform-action' {
            tailf:xpath-root 3;
          }
          tailf:cli-optional-in-sequence;
          type empty;
        }
        leaf exceed-action {
          tailf:info
            "action when rate is within conform and conform + exceed burst";
          type empty;
        }
        leaf drop {
          tailf:info
            "drop packet";
          when '../exceed-action' {
            tailf:xpath-root 3;
          }
          tailf:cli-optional-in-sequence;
          tailf:cli-full-command;
          type empty;
        }
        container exceed-transmit {
          tailf:cli-no-keyword;
          tailf:cli-drop-node-name;
          tailf:cli-optional-in-sequence;
          tailf:cli-flatten-container;
          leaf transmit {
            tailf:info
              "transmit packet";
            when '../../exceed-action' {
              tailf:xpath-root 3;
            }
            tailf:cli-optional-in-sequence;
            type empty;
          }
        }
      }
    }
    list class-map {
      tailf:ncs-device-type "cli-ned";
      tailf:display-when "not(../ncs:module) or ../ncs:module[ncs:name='tailf-ned-cisco-ios']";
      tailf:info
        "Configure QoS Class Map";
      tailf:cli-mode-name "config-cmap";
      tailf:cli-suppress-list-no;
      tailf:cli-delete-when-empty;
      tailf:cli-no-key-completion;
      key "name";
      leaf name {
        type string {
          tailf:info
            "WORD;;class-map name";
        }
        tailf:cli-disallow-value "type";
      }
      leaf type {
        tailf:info
          "type of the class-map";
        tailf:cli-prefix-key;
        type enumeration {
          enum "inspect";
        }
      }
      leaf protocol {
        tailf:cli-drop-node-name;
        tailf:cli-prefix-key;
        type enumeration {
          enum "aol" {
            tailf:info
              "Configure CBAC class-map for IM-AOL protocol";
          }
          enum "edonkey" {
            tailf:info
              "eDonkey";
          }
          enum "fasttrack" {
            tailf:info
              "FastTrack Traffic - KaZaA, Morpheus, Grokster...";
          }
          enum "gnutella" {
            tailf:info
              "Gnutella Version2 Traffic - BearShare, Shareeza, Morpheus ...";
          }
          enum "http" {
            tailf:info
              "Configure CBAC class-map for HTTP protocol";
          }
          enum "imap" {
            tailf:info
              "Configure CBAC class-map for IMAP protocol";
          }
          enum "kazaa2" {
            tailf:info
              "Kazaa Version 2";
          }
          enum "msnmsgr" {
            tailf:info
              "Configure CBAC class-map for IM-MSN protocol";
          }
          enum "pop3" {
            tailf:info
              "Configure CBAC class-map for POP3 protocol";
          }
          enum "smtp" {
            tailf:info
              "Configure CBAC class-map for SMTP protocol";
          }
          enum "sunrpc" {
            tailf:info
              "Configure CBAC class-map for RPC protocol";
          }
          enum "ymsgr" {
            tailf:info
              "Configure CBAC class-map for IM-YAHOO protocol";
          }
        }
      }
      leaf prematch {
        tailf:cli-no-keyword;
        tailf:cli-prefix-key;
        tailf:cli-drop-node-name;
        type enumeration {
          enum "match-all" {
            tailf:info
              "Logical-AND all matching statements under this classmap";
          }
          enum "match-any" {
            tailf:info
              "Logical-OR all matching statements under this classmap";
          }
        }
        mandatory true;
      }
      leaf description {
        tailf:info
          "Class-Map description";
        tailf:cli-multi-value;
        type string {
          tailf:info
            "LINE;;Description of this class-map (up to 200 characters)";
        }
      }
      container match {
        tailf:info
          "classification criteria";
        uses class-map-match-grouping;
        container not {
          tailf:info
            "Negate this match result";
          uses class-map-match-grouping;
        }
      }
    }
    list policy-map {
      tailf:ncs-device-type "cli-ned";
      tailf:display-when "not(../ncs:module) or ../ncs:module[ncs:name='tailf-ned-cisco-ios']";
      tailf:info
        "Configure QoS Policy Map";
      tailf:cli-mode-name "config-pmap";
      tailf:cli-diff-dependency "/ios:class-map" {
        tailf:xpath-root 3;
      }
      tailf:cli-diff-dependency "/ios:table-map" {
        tailf:xpath-root 3;
      }
      tailf:cli-diff-dependency "/ios:mls/qos/aggregate-policer" {
        tailf:xpath-root 3;
      }
      tailf:cli-diff-dependency "/ios:policer/aggregate" {
        tailf:xpath-root 3;
      }
      key "name";
      leaf name {
        type string {
          tailf:info
            "WORD;;policy-map name";
        }
        tailf:cli-disallow-value "(type)|(http)|(im)|(imap)|(p2p)|(pop3)|(smtp)|(sunrpc)";
      }
      leaf type {
        tailf:info
          "type of the policy-map";
        tailf:cli-prefix-key;
        type enumeration {
          enum "inspect";
        }
      }
      leaf protocol {
        tailf:cli-drop-node-name;
        tailf:cli-prefix-key;
        type enumeration {
          enum "http" {
            tailf:info
              "Configure CBAC policy-map for HTTP protocol";
          }
          enum "im" {
            tailf:info
              "Configure CBAC policy-map for IM protocol";
          }
          enum "imap" {
            tailf:info
              "Configure CBAC policy-map for IMAP protocol";
          }
          enum "p2p" {
            tailf:info
              "Configure CBAC policy-map for P2P protocols";
          }
          enum "pop3" {
            tailf:info
              "Configure CBAC policy-map for POP3 protocol";
          }
          enum "smtp" {
            tailf:info
              "Configure CBAC policy-map for SMTP protocol";
          }
          enum "sunrpc" {
            tailf:info
              "Configure CBAC policy-map for RPC protocol";
          }
        }
      }
      list class {
        tailf:info
          "policy criteria";
        tailf:cli-mode-name "config-pmap-c";
        key "name";
        leaf name {
          tailf:cli-disallow-value "type";
          type class-name-type;
        }
        leaf type {
          tailf:info
            "type of the class-map";
          tailf:cli-prefix-key;
          type enumeration {
            enum "inspect" {
              tailf:info
                "Configure CBAC Class Map";
            }
          }
        }
        container policy {
          when "../../type = 'inspect'" {
            tailf:xpath-root 3;
          }
          tailf:cli-drop-node-name;
          tailf:cli-sequence-commands {
            tailf:cli-reset-siblings;
          }
          leaf action {
            tailf:cli-drop-node-name;
            tailf:cli-remove-before-change;
            type enumeration {
              enum "drop" {
                tailf:info
                  "Drop the packet";
              }
              enum "inspect" {
                tailf:info
                  "Context-based Access Control Engine";
              }
              enum "pass" {
                tailf:info
                  "Pass the packet";
              }
            }
          }
          leaf log {
            tailf:info
              "Send logging message for drop";
            when "../action = 'drop'" {
              tailf:xpath-root 3;
            }
            type empty;
          }
          leaf parameter-map {
            tailf:cli-drop-node-name;
            when "../action = 'inspect'" {
              tailf:xpath-root 3;
            }
            type string;
            tailf:non-strict-leafref {
              path "/ncs:devices/ncs:device/ncs:config/ios:parameter-map/type/inspect/id" {
                tailf:xpath-root 3;
              }
            }
          }
        }
        container inspect-police {
          when "../policy/action = 'inspect'" {
            tailf:xpath-root 3;
          }
          tailf:cli-drop-node-name;
          container police {
            tailf:info
              "Police";
            tailf:cli-sequence-commands {
              tailf:cli-reset-siblings;
            }
            tailf:cli-compact-syntax;
            leaf rate {
              tailf:info
                "Specify police rate";
              type uint32 {
                tailf:info
                  "<8000-2000000000>;;Rate value in bps";
                range "8000..2000000000";
              }
            }
            leaf burst {
              tailf:info
                "Specify 'burst' parameter";
              type uint32 {
                tailf:info
                  "<1000-512000000>;;Burst value in bytes";
                range "1000..512000000";
              }
            }
          }
        }
        container bandwidth {
          tailf:info
            "Bandwidth";
          leaf bits {
            tailf:cli-drop-node-name;
            type uint32 {
              range "8..2000000";
              tailf:info
                "<8-2000000>;;Kilo Bits per second";
            }
          }
          leaf percent {
            tailf:info
              "% of total Bandwidth";
            type percentage-type;
          }
          container remaining {
            tailf:info
              "% of the remaining bandwidth";
            leaf percent {
              tailf:info
                "% of the remaining bandwidth";
              type percentage-type;
            }
          }
        }
        container compression {
          tailf:info
            "Activate Compression";
          presence "Activate Compression";
          container header {
            tailf:info
              "configure header compression";
            presence "configure header compression";
            leaf ip {
              tailf:info
                "configure ip header compression";
              type enumeration {
                enum "rtp" {
                  tailf:code-name "header_rtp";
                  tailf:info
                    "configure rtp header compression";
                }
                enum "tcp" {
                  tailf:info
                    "configure tcp header compression";
                }
              }
            }
          }
        }
        leaf drop {
          tailf:info
            "Drop all packets";
          tailf:cli-full-command;
          type empty;
        }
        container estimate {
          tailf:info
            "estimate resources required for this class";
          container bandwidth {
            presence "bandwidth required to service this class";
            tailf:info
              "bandwidth required to service this class";
            tailf:cli-sequence-commands;
            tailf:cli-compact-syntax;
            container delay-one-in {
              tailf:info
                "specify QoS target delay";
              tailf:cli-compact-syntax;
              tailf:cli-sequence-commands;
              leaf doi {
                tailf:cli-drop-node-name;
                tailf:cli-incomplete-command;
                type uint32 {
                  range "50..1000000";
                  tailf:info
                    "<50-1000000>;;delay one packet of N";
                }
              }
              leaf milliseconds {
                type uint32 {
                  range "8..1000" {
                    tailf:info
                      "<8-1000>;;worst-case milliseconds of delay";
                  }
                }
              }
            }
            leaf drop-one-in {
              tailf:info
                "specify QoS target loss rate";
              type uint32 {
                tailf:info
                  "<50-1000000>;;drop one packet of N";
              }
            }
          }
        }
        container fair-queue {
          tailf:info
            "Enable Flow-based Fair Queuing in this Class";
          tailf:cli-reset-container;
          presence "true";
          leaf dynamic-queues {
            tailf:cli-drop-node-name;
            tailf:cli-full-command;
            type uint32 {
              range "16|32|64|128|256|512|1024|2048|4096" {
                tailf:info
                  "<16-4096>;;Number Dynamic Conversation Queues";
              }
            }
          }
          leaf queue-limit {
            tailf:info
              "per flow queue limit";
            tailf:cli-full-command;
            type uint16 {
              tailf:info
                "<1-32768>;;packets";
              range "1..32768";
            }
          }
        }
        leaf netflow-sampler {
          tailf:info
            "NetFlow action";
          tailf:cli-full-command;
          type string {
            tailf:info
              "WORD;;Name of the flow sampler";
          }
        }
        choice police-choice {
          case police-aggregate-case {
            container police-aggregate {
              tailf:cli-no-keyword;
              tailf:cli-drop-node-name;
              container police {
                tailf:info
                  "Police";
                leaf aggregate {
                  tailf:info
                    "Choose aggregate policer for current class";
                  type string {
                    tailf:info
                      "WORD;;enter aggregate-policer name";
                  }
                }
              }
            }
          }
          case police-policy-map-case {
            container police-policy-map {
              tailf:cli-no-keyword;
              tailf:cli-drop-node-name;
              container police {
                tailf:cli-add-mode;
                tailf:cli-mode-name "config-pmap-c-police";
                tailf:cli-flatten-container;
                tailf:cli-sequence-commands {
                  tailf:cli-reset-siblings;
                }
                leaf cir {
                  tailf:info
                    "Committed information rate";
                  tailf:cli-hide-in-submode;
                  type police-bps-type;
                }
                leaf bc {
                  tailf:info
                    "Conform burst";
                  tailf:cli-optional-in-sequence;
                  tailf:cli-hide-in-submode;
                  type police-burst-type;
                }
                leaf be {
                  when '../bc' {
                    tailf:xpath-root 3;
                  }
                  tailf:info
                    "Excess burst";
                  tailf:cli-optional-in-sequence;
                  tailf:cli-hide-in-submode;
                  type police-burst-type;
                }
                leaf pir {
                  tailf:info
                    "Peak Information Rate";
                  tailf:cli-optional-in-sequence;
                  tailf:cli-hide-in-submode;
                  type police-bps-type;
                }
                container pir-be {
                  when '../pir' {
                    tailf:xpath-root 3;
                  }
                  tailf:cli-no-keyword;
                  tailf:cli-drop-node-name;
                  tailf:cli-optional-in-sequence;
                  tailf:cli-flatten-container;
                  tailf:cli-hide-in-submode;
                  leaf be {
                    tailf:info
                      "Excess burst";
                    type police-burst-type;
                  }
                }
                uses police-action-grouping;
              }
            }
          }
          case police-cir-percent-case {
            container police-cir-percent {
              tailf:cli-no-keyword;
              tailf:cli-drop-node-name;
              container police {
                container cir {
                  tailf:info
                    "Committed information rate";
                  container percent {
                    tailf:info
                      "% of interface bandwidth for Committed information rate";
                    tailf:cli-add-mode;
                    tailf:cli-mode-name "config-pmap-c-police";
                    tailf:cli-incomplete-command;
                    tailf:cli-flatten-container;
                    tailf:cli-sequence-commands {
                      tailf:cli-reset-siblings;
                    }
                    leaf percentage {
                      tailf:cli-drop-node-name;
                      tailf:cli-hide-in-submode;
                      type percentage-type;
                    }
                    leaf bc {
                      tailf:info
                        "Conform burst";
                      tailf:cli-optional-in-sequence;
                      tailf:cli-hide-in-submode;
                      type uint16 {
                        tailf:info
                          "<1-2000>;;Burst ms";
                      }
                    }
                    container bc-ms {
                      when '../bc' {
                        tailf:xpath-root 3;
                      }
                      tailf:cli-no-keyword;
                      tailf:cli-drop-node-name;
                      tailf:cli-optional-in-sequence;
                      tailf:cli-hide-in-submode;
                      tailf:cli-compact-syntax;
                      tailf:cli-flatten-container;
                      leaf ms {
                        tailf:info
                          "Milli seconds";
                        tailf:cli-no-keyword;
                        type empty;
                      }
                    }
                    leaf be {
                      when '../bc-ms/ms' {
                        tailf:xpath-root 3;
                        tailf:dependency "../bc-ms/ms";
                      }
                      tailf:info
                        "Excess burst";
                      tailf:cli-optional-in-sequence;
                      tailf:cli-hide-in-submode;
                      type uint16 {
                        tailf:info
                          "<1-2000>;;Burst ms";
                      }
                    }
                    container be-ms {
                      when '../be' {
                        tailf:xpath-root 3;
                      }
                      tailf:cli-no-keyword;
                      tailf:cli-drop-node-name;
                      tailf:cli-hide-in-submode;
                      tailf:cli-compact-syntax;
                      tailf:cli-flatten-container;
                      leaf ms {
                        tailf:info
                          "Milli seconds";
                        tailf:cli-no-keyword;
                        type empty;
                      }
                    }
                    container pir {
                      tailf:info
                        "Peak Information Rate";
                      tailf:cli-compact-syntax;
                      tailf:cli-flatten-container;
                      tailf:cli-hide-in-submode;
                      tailf:cli-optional-in-sequence;
                      leaf percent {
                        tailf:info
                          "% of interface bandwidth for Peak Information Rate";
                        type percentage-type;
                      }
                    }
                    container pir-be {
                      when '../pir' {
                        tailf:xpath-root 3;
                      }
                      tailf:cli-no-keyword;
                      tailf:cli-drop-node-name;
                      tailf:cli-optional-in-sequence;
                      tailf:cli-flatten-container;
                      tailf:cli-hide-in-submode;
                      leaf be {
                        tailf:info
                          "Excess burst";
                        type uint16 {
                          tailf:info
                            "<1-2000>;;Burst ms";
                        }
                      }
                    }
                    container pir-be-ms {
                      when '../pir-be/be' {
                        tailf:xpath-root 3;
                        tailf:dependency "../pir-be/be";
                      }
                      tailf:cli-no-keyword;
                      tailf:cli-drop-node-name;
                      tailf:cli-optional-in-sequence;
                      tailf:cli-hide-in-submode;
                      tailf:cli-flatten-container;
                      leaf ms {
                        tailf:info
                          "Milli seconds";
                        tailf:cli-no-keyword;
                        type empty;
                      }
                    }
                    uses police-action-grouping;
                  }
                }
              }
            }
          }
          case police-rate-unit-case {
            container police-rate-unit {
              tailf:cli-no-keyword;
              tailf:cli-drop-node-name;
              container police {
                container rate {
                  tailf:info
                    "Specify police rate";
                  tailf:cli-add-mode;
                  tailf:cli-mode-name "config-pmap-c-police";
                  tailf:cli-flatten-container;
                  tailf:cli-sequence-commands {
                    tailf:cli-reset-siblings;
                  }
                  leaf units {
                    tailf:cli-drop-node-name;
                    tailf:cli-hide-in-submode;
                    type uint64 {
                      tailf:info
                        "<1-2000000000>;;Rate value in the range 8000-2,000,000,000 bps or 1-2,000,000 pps";
                    }
                  }
                  leaf xps {
                    tailf:cli-no-keyword;
                    tailf:cli-drop-node-name;
                    tailf:cli-hide-in-submode;
                    type police-pps-bps-type;
                  }
                  container burst {
                    tailf:info
                      "Specify 'burst' parameter";
                    tailf:cli-optional-in-sequence;
                    tailf:cli-compact-syntax;
                    tailf:cli-hide-in-submode;
                    tailf:cli-flatten-container;
                    tailf:cli-sequence-commands;
                    leaf burst-value {
                      tailf:cli-no-keyword;
                      tailf:cli-drop-node-name;
                      tailf:cli-incomplete-command;
                      type uint32 {
                        tailf:info
                          "<1-512000000>;;Burst value in packets/bytes";
                      }
                    }
                    leaf burst-type {
                      tailf:cli-no-keyword;
                      tailf:cli-drop-node-name;
                      tailf:cli-hide-in-submode;
                      type police-packets-bytes-type;
                    }
                  }
                  container peak-rate {
                    tailf:info
                      "Specify peak rate";
                    tailf:cli-optional-in-sequence;
                    tailf:cli-compact-syntax;
                    tailf:cli-flatten-container;
                    tailf:cli-hide-in-submode;
                    tailf:cli-sequence-commands;
                    leaf peak-rate-value {
                      tailf:cli-no-keyword;
                      tailf:cli-drop-node-name;
                      tailf:cli-incomplete-command;
                      type uint32 {
                        tailf:info
                          "<1-512000000>;;Peak-rate value in packets or bytes per second";
                        range "1..512000000";
                      }
                    }
                    leaf xps {
                      tailf:cli-no-keyword;
                      tailf:cli-drop-node-name;
                      type police-pps-bps-type;
                    }
                  }
                  container peak-burst {
                    tailf:info
                      "Specify 'peak-burst' parameter for peak-rate";
                    tailf:cli-optional-in-sequence;
                    tailf:cli-compact-syntax;
                    tailf:cli-flatten-container;
                    tailf:cli-hide-in-submode;
                    tailf:cli-sequence-commands;
                    leaf burst-value {
                      tailf:cli-no-keyword;
                      tailf:cli-drop-node-name;
                      tailf:cli-incomplete-command;
                      type uint32 {
                        tailf:info
                          "<1-512000000>;;Burst value in packets/bytes";
                      }
                    }
                    leaf burst-type {
                      tailf:cli-no-keyword;
                      tailf:cli-drop-node-name;
                      type police-packets-bytes-type;
                    }
                  }
                  uses police-action-grouping;
                }
              }
            }
          }
          case police-rate-percent-case {
            container police-rate-percent {
              tailf:cli-no-keyword;
              tailf:cli-drop-node-name;
              container police {
                container rate {
                  tailf:info
                    "Specify police rate";
                  container percent {
                    tailf:info
                      "% of interface bandwidth for rate";
                    tailf:cli-add-mode;
                    tailf:cli-mode-name "config-pmap-c-police";
                    tailf:cli-flatten-container;
                    tailf:cli-sequence-commands {
                      tailf:cli-reset-siblings;
                    }
                    leaf percentage {
                      tailf:cli-drop-node-name;
                      tailf:cli-hide-in-submode;
                      type percentage-type;
                    }
                    leaf burst {
                      tailf:info
                        "Specify 'burst' parameter";
                      tailf:cli-optional-in-sequence;
                      tailf:cli-hide-in-submode;
                      type uint16 {
                        tailf:info
                          "<1-2000>;;Burst value in milliseconds";
                      }
                    }
                    leaf ms {
                      when '../burst' {
                        tailf:xpath-root 3;
                      }
                      tailf:info
                        "Treat 'burst' value in milliseconds";
                      tailf:cli-hide-in-submode;
                      type empty;
                    }
                    container peak-rate {
                      tailf:info
                        "Specify peak rate";
                      tailf:cli-hide-in-submode;
                      tailf:cli-optional-in-sequence;
                      tailf:cli-flatten-container;
                      leaf percent {
                        tailf:info
                          "% of interface bandwidth for peak-rate";
                        type percentage-type;
                      }
                    }
                    leaf peak-burst {
                      tailf:info
                        "Specify 'peak-burst' parameter for 'peak-rate'";
                      tailf:cli-hide-in-submode;
                      tailf:cli-optional-in-sequence;
                      type uint16 {
                        tailf:info
                          "<1-2000>;;Peak burst value in milliseconds";
                      }
                    }
                    container peak-burst-ms {
                      when '../peak-burst' {
                        tailf:xpath-root 3;
                      }
                      tailf:cli-no-keyword;
                      tailf:cli-drop-node-name;
                      tailf:cli-optional-in-sequence;
                      tailf:cli-hide-in-submode;
                      tailf:cli-flatten-container;
                      leaf ms {
                        tailf:info
                          "Milli seconds";
                        tailf:cli-no-keyword;
                        type empty;
                      }
                    }
                    uses police-action-grouping;
                  }
                }
              }
            }
          }
          case police-rate-pdp-case {
            container police-rate-pdp {
              tailf:cli-no-keyword;
              tailf:cli-drop-node-name;
              container police {
                container rate {
                  tailf:info
                    "Specify police rate";
                  container pdp {
                    tailf:info
                      "% of interface bandwidth for rate";
                    tailf:cli-add-mode;
                    tailf:cli-mode-name "config-pmap-c-police";
                    tailf:cli-flatten-container;
                    tailf:cli-sequence-commands {
                      tailf:cli-reset-siblings;
                    }
                    leaf burst {
                      tailf:info
                        "Conform burst";
                      tailf:cli-hide-in-submode;
                      tailf:cli-optional-in-sequence;
                      type police-burst-type;
                    }
                    leaf peak-rate {
                      tailf:info
                        "Specify peak rate";
                      tailf:cli-hide-in-submode;
                      tailf:cli-optional-in-sequence;
                      type enumeration {
                        enum "pdp";
                      }
                    }
                    leaf peak-burst {
                      when '../peak-rate' {
                        tailf:xpath-root 3;
                      }
                      tailf:info
                        "Specify 'peak-burst' parameter for 'peak-rate'";
                      tailf:cli-hide-in-submode;
                      tailf:cli-optional-in-sequence;
                      type police-burst-type;
                    }
                    uses police-action-grouping;
                  }
                }
              }
            }
          }
          case police-flow-case {
            container police-flow {
              tailf:cli-no-keyword;
              tailf:cli-drop-node-name;
              container police {
                container flow {
                  tailf:info
                    "police each flow";
                  tailf:cli-add-mode;
                  tailf:cli-mode-name "config-pmap-c-police";
                  tailf:cli-flatten-container;
                  tailf:cli-sequence-commands {
                    tailf:cli-reset-siblings;
                  }
                  leaf mask {
                    tailf:info
                      "flow mask to be used for policing";
                    tailf:cli-hide-in-submode;
                    tailf:cli-optional-in-sequence;
                    type enumeration {
                      enum "dest-only" {
                        tailf:info
                          "destination-address only flow mask";
                      }
                      enum "full-flow" {
                        tailf:info
                          "full flow mask";
                      }
                      enum "src-only" {
                        tailf:info
                          "source-address only flow mask";
                      }
                    }
                  }
                  leaf bps {
                    tailf:cli-drop-node-name;
                    tailf:cli-hide-in-submode;
                    type police-bps-type;
                  }
                  leaf burst-normal {
                    when '../bps' {
                      tailf:xpath-root 3;
                    }
                    tailf:cli-drop-node-name;
                    tailf:cli-hide-in-submode;
                    tailf:cli-optional-in-sequence;
                    type police-burst-type;
                  }
                  uses police-action-grouping;
                }
              }
            }
          }
          case police-catalyst-case {
            container police-catalyst {
              tailf:cli-no-keyword;
              tailf:cli-drop-node-name;
              container police {
                tailf:cli-add-mode;
                tailf:cli-mode-name "config-pmap-c-police";
                tailf:cli-flatten-container;
                tailf:cli-sequence-commands {
                  tailf:cli-reset-siblings;
                }
                leaf bps-value {
                  tailf:cli-no-keyword;
                  tailf:cli-drop-node-name;
                  tailf:cli-hide-in-submode;
                  tailf:cli-incomplete-command;
                  type string {
                    tailf:info
                      "<32000-32000000000>;;Rate in bits per second (postfix k, m, g optional; decimal point allowed)";
                  }
                }
                leaf bps {
                  tailf:cli-hide-in-submode;
                  tailf:cli-incomplete-command;
                  type empty;
                }
                leaf byte-value {
                  tailf:cli-no-keyword;
                  tailf:cli-drop-node-name;
                  tailf:cli-hide-in-submode;
                  tailf:cli-incomplete-command;
                  type string {
                    tailf:info
                      "<32000-32000000000>;;(postfix k, m, g optional; decimal point allowed)";
                  }
                }
                leaf byte {
                  tailf:cli-hide-in-submode;
                  type empty;
                }
                container actions {
                  tailf:cli-no-keyword;
                  tailf:cli-break-sequence-commands;
                  tailf:cli-drop-node-name;
                  tailf:cli-flatten-container;
                  tailf:cli-hide-in-submode;
                  uses police-conform-action-grouping;
                  uses police-exceed-action-grouping;
                  uses police-violate-action-grouping;
                }
              }
            }
          }
          case police-switch-case {
            container police-switch {
              tailf:cli-no-keyword;
              tailf:cli-drop-node-name;
              container police {
                tailf:cli-compact-syntax;
                tailf:cli-sequence-commands {
                  tailf:cli-reset-siblings;
                }
                leaf cir {
                  tailf:cli-incomplete-command;
                  tailf:cli-drop-node-name;
                  type uint32 {
                    tailf:info
                      "<8000-1000000000>;;Bits per second";
                    range "8000..1000000000";
                  }
                }
                leaf bc {
                  tailf:cli-drop-node-name;
                  type uint32 {
                    tailf:info
                      "<8000-2000000>;;Normal burst bytes";
                    range "8000..2000000";
                  }
                }
                leaf exceed-action {
                  tailf:info
                    "action when rate is exceeded";
                  type enumeration {
                    enum "drop" {
                      tailf:info
                        "drop packet";
                    }
                    enum "policed-dscp-transmit" {
                      tailf:info
                        "change dscp per policed-dscp map and send it";
                    }
                  }
                }
              }
            }
          }
        }
        container priority {
          tailf:info
            "Strict Scheduling Priority for this Class";
          tailf:cli-compact-syntax;
          tailf:cli-sequence-commands;
          presence "true";
          leaf level {
            tailf:info
              "Multi-Level Priority Queue";
            tailf:cli-optional-in-sequence;
            type uint8 {
              tailf:info
                "<1-2>;;Multi-Level Priority Queue";
              range "1..2";
            }
          }
          choice priority-type {
            leaf kilo-bits {
              tailf:cli-drop-node-name;
              type uint32 {
                range "8..2000000";
                tailf:info
                  "<8-2000000>;;Kilo Bits per second";
              }
            }
            leaf percent {
              tailf:info
                "% of total bandwidth";
              type uint16 {
                range "1..100";
                tailf:info
                  "<1-100>;;percentage";
              }
            }
          }
          leaf burst {
            tailf:cli-drop-node-name;
            type uint32 {
              tailf:info
                "<32-64000000>;;Burst in bytes";
              range "32..64000000";
            }
          }
        }
        container queue-limit {
          tailf:info
            "Queue Max Threshold for Tail Drop";
          tailf:cli-compact-syntax;
          tailf:cli-sequence-commands {
            tailf:cli-reset-siblings;
          }
          leaf queue-limit-value {
            tailf:cli-drop-node-name;
            type uint32 {
              tailf:info
                "<1-8192000>  in bytes, <1-3400> in ms, <1-32768> in packets by default";
              range "1..8192000";
            }
          }
          leaf queue-limit-type {
            tailf:cli-drop-node-name;
            type enumeration {
              enum "bytes" {
                tailf:info
                  "in bytes";
              }
              enum "ms" {
                tailf:info
                  "in milliseconds";
              }
              enum "packets" {
                tailf:info
                  "in packets";
              }
            }
          }
        }
        container random-detect {
          tailf:info
            "Enable Random Early Detection as drop policy";
          presence "true";
          container aggregate {
            tailf:info
              "aggregate subclasses";
            tailf:cli-compact-syntax;
            tailf:cli-sequence-commands {
              tailf:cli-reset-siblings;
            }
            presence "true";
            leaf minimum-thresh {
              tailf:info
                "minimum threshold for red aggregate";
              type uint32 {
                tailf:info
                  "<0-1000000>;;minimum threshold (number of packets)";
                range "0..1000000";
              }
            }
            leaf maximum-thresh {
              tailf:info
                "maximum threshold for red aggregate";
              type uint32 {
                tailf:info
                  "<0-1000000>;;maximum threshold (number of packets)";
                range "0..1000000";
              }
            }
            leaf mark-probability {
              tailf:info
                "mark-probability for red aggregate";
              type empty;
            }
            leaf denominator {
              tailf:cli-drop-node-name;
              type uint32 {
                tailf:info
                  "<0-65535>;;mark probability denominator";
                range "0..65535";
              }
            }
          }
          container discard-class {
            tailf:info
              "parameters for each discard-class value";
            tailf:cli-compact-syntax;
            tailf:cli-sequence-commands;
            leaf dclass {
              tailf:cli-drop-node-name;
              tailf:cli-incomplete-command;
              type uint16 {
                range "0..7";
                tailf:info
                  "<0-7>;;discard-class value";
              }
            }
            uses random-detect-grouping;
          }
          leaf discard-class-based {
            tailf:info
              "Enable discard-class-based WRED as drop policy";
            tailf:cli-full-command;
            type empty;
          }
          container dscp {
            tailf:info
              "parameters for each dscp value";
            tailf:cli-sequence-commands;
            tailf:cli-compact-syntax;
            leaf dscp-val {
              tailf:cli-drop-node-name;
              tailf:cli-incomplete-command;
              type dscp-type;
            }
            uses random-detect-grouping;
          }
          leaf dscp-based {
            tailf:info
              "Enable dscp-based WRED as drop policy";
            tailf:cli-full-command;
            type empty;
          }
          leaf ecn {
            tailf:info
              "explicit congestion notification";
            tailf:cli-full-command;
            type empty;
          }
          leaf exponential-weighting-constant {
            tailf:info
              "weight for mean queue depth calculation";
            tailf:cli-full-command;
            type uint16 {
              range "1..16";
              tailf:info
                "<1-16>;;integer in 1..16 used in weighted average to mean 2^number";
            }
          }
          leaf prec-based {
            tailf:info
              "Enable precedence-based WRED as drop policy";
            tailf:cli-full-command;
            type empty;
          }
          container precedence {
            tailf:info
              "parameters for each precedence value";
            tailf:cli-sequence-commands;
            tailf:cli-compact-syntax;
            leaf prec {
              tailf:cli-drop-node-name;
              tailf:cli-incomplete-command;
              type precedence-type2;
            }
            uses random-detect-grouping;
          }
        }
        leaf service-policy {
          tailf:info
            "Configure Flow Next";
          tailf:cli-full-command;
          type string;
          tailf:non-strict-leafref {
            path "/ncs:devices/ncs:device/ncs:config/ios:policy-map/name" {
              tailf:xpath-root 3;
            }
          }
        }
        container set {
          tailf:info
            "Set QoS values";
          leaf atm-clp {
            tailf:info
              "Set ATM CLP bit to 1";
            tailf:cli-full-command;
            type empty;
          }
          container cos {
            tailf:info
              "Set IEEE 802.1Q/ISL class of service/user priority";
            tailf:cli-compact-syntax;
            tailf:cli-sequence-commands;
            choice cos-type {
              case a {
                leaf val {
                  tailf:cli-drop-node-name;
                  type uint16 {
                    range "0..7";
                    tailf:info
                      "<0-7>;;cos value";
                  }
                }
              }
              case b {
                leaf pack {
                  tailf:cli-drop-node-name;
                  type enumeration {
                    enum "dscp" {
                      tailf:code-name "pack_dscp";
                      tailf:info
                        "Set value from packet dscp";
                    }
                    enum "precedence" {
                      tailf:code-name "pack_precedence";
                      tailf:info
                        "Set value from packet precedence.";
                    }
                  }
                }
                leaf table {
                  tailf:info
                    "Set codepoint value based on tablemap.";
                  type string {
                    tailf:info
                      "WORD;;table-map name";
                  }
                  tailf:non-strict-leafref {
                    path "/ncs:devices/ncs:device/ncs:config/ios:table-map/name" {
                      tailf:xpath-root 3;
                    }
                  }
                }
              }
            }
          }
          leaf discard-class {
            tailf:info
              "Discard behavior identifier";
            tailf:cli-full-command;
            type uint16 {
              range "0..7";
              tailf:info
                "<0-7>;;Discard Class value";
            }
          }
          leaf dscp {
            tailf:info
              "Set DSCP in IP(v4) and IPv6 packets";
            tailf:cli-full-command;
            type dscp-type;
          }
          leaf fr-de {
            tailf:info
              "Set FR DE bit to 1";
            tailf:cli-full-command;
            type empty;
          }
          container ip {
            tailf:info
              "Set IP specific values";
            choice ip-choice {
              leaf dscp {
                tailf:info
                  "Set IP DSCP (DiffServ CodePointint)";
                type dscp-type;
              }
              container precedence {
                tailf:info
                  "Set IP precedence";
                presence "Set IP precedence";
                leaf precedence-val {
                  tailf:cli-drop-node-name;
                  type precedence-type;
                }
              }
            }
          }
          container mpls {
            tailf:info
              "Set MPLS specific values";
            container experimental {
              tailf:info
                "Set Experimental value";
              container imposition {
                tailf:info
                  "Set Experimental value at tag imposition";
                leaf exp-value {
                  tailf:cli-drop-node-name;
                  tailf:cli-full-command;
                  type uint8 {
                    tailf:info
                      "<0-7>;;Experimental value";
                    range "0..7";
                  }
                }
              }
            }
          }
          container qos-group {
            tailf:info
              "Set QoS Group";
            leaf qos-group-value {
              tailf:cli-drop-node-name;
              tailf:cli-full-command;
              type uint8 {
                range "0..99";
              }
            }
          }
        }
        container shape {
          tailf:info
            "Traffic Shaping";
          leaf adaptive {
            tailf:info
              "Enable Traffic Shaping adaptation to BECN";
            tailf:cli-full-command;
            type uint32 {
              range "8000..154400000";
              tailf:info
                "<8000-154400000>;;Lower Bound Target Bit Rate (bits per second)";
            }
          }
          container average {
            tailf:info
              "configure token bucket: CIR (bps) [Bc (bits) [Be (bits)]], send out Bc only per interval";
            tailf:cli-sequence-commands;
            tailf:cli-compact-syntax;
            choice average-choice {
              case a {
                leaf bit-rate {
                  tailf:cli-drop-node-name;
                  type uint32 {
                    tailf:info
                      "<8000-max>;;Target Bit Rate (bits per second), the value needs to be a multiple of 8000";
                  }
                }
                leaf bits-per-interval-sustained {
                  tailf:cli-drop-node-name;
                  type uint32 {
                    range "256..154400000";
                    tailf:info
                      "<256-154400000>;;bits per interval, sustained. Needs to be multiple of 128. Recommend not to configure it, the algorithm will find out the best value";
                  }
                }
                leaf bits-per-interval-excess {
                  tailf:cli-drop-node-name;
                  type uint32 {
                    range "0..154400000";
                    tailf:info
                      "<0-154400000>;;bits per interval, excess. Needs to be multiple of 128. Bc will be used if you don't configure it.";
                  }
                }
              }
              case b {
                leaf percent {
                  tailf:info
                    "% of interface bandwidth for Committed information rate";
                  type percentage-type;
                }
                leaf burst-size-sustained {
                  tailf:cli-incomplete-command;
                  tailf:cli-drop-node-name;
                  type uint16 {
                    range "10..2000";
                    tailf:info
                      "<10-2000>;;Sustained burst size in msec";
                  }
                }
                leaf ms {
                  tailf:info
                    "milliseconds";
                  type empty;
                }
                container bse {
                  tailf:cli-drop-node-name;
                  tailf:cli-flatten-container;
                  tailf:cli-sequence-commands;
                  tailf:cli-compact-syntax;
                  leaf burst-size-excess {
                    tailf:cli-incomplete-command;
                    type uint16 {
                      range "10..2000";
                      tailf:info
                        "<10-2000>;;Excess burst size in msec";
                    }
                  }
                  leaf ms {
                    tailf:info
                      "milliseconds";
                    type empty;
                  }
                }
              }
            }
          }
          leaf fecn-adapt {
            tailf:info
              "Enable Traffic Shaping reflection of FECN as BECN";
            tailf:cli-full-command;
            type empty;
          }
          container fr-voice-adapt {
            tailf:info
              "Enable rate adjustment depending on voice presence";
            presence "Enable rate adjustment depending on voice presence";
            leaf deactivation {
              type uint16 {
                range "1..10000";
                tailf:info
                  "<1-10000>;;de-activation delay in seconds";
              }
            }
          }
          leaf max-buffers {
            tailf:cli-full-command;
            tailf:info
              "Set Maximum Buffer Limit";
            type uint16 {
              range "1..4096";
              tailf:info
                "<1-4096>;;Maximum Buffer Limit";
            }
          }
        }
        leaf trust {
          tailf:info
            "Set trust value for the class";
          type enumeration {
            enum "cos" {
              tailf:info
                "trust value for the class";
            }
            enum "dscp" {
              tailf:info
                "trust value for the class";
            }
            enum "ip-precedence" {
              tailf:info
                "trust value for the class";
            }
          }
        }
      }
      leaf description {
        tailf:info
          "Policy-Map description";
        tailf:cli-multi-value;
        type string {
          length "1..200";
          tailf:info
            "LINE;;Description of this policy-map (up to 200 characters)";
        }
      }
    }
    container control-plane {
      tailf:ncs-device-type "cli-ned";
      tailf:display-when "not(../../ncs:module) or ../../ncs:module[ncs:name='tailf-ned-cisco-ios']";
      tailf:info
        "Configure control plane services";
      tailf:cli-add-mode;
      tailf:cli-mode-name "config-cp";
      presence "true";
      container service-policy {
        leaf input {
          tailf:info
            "Assign policy-map to the input of an interface";
          type string {
            tailf:info
              "WORD;;Policy map name";
          }
          tailf:non-strict-leafref {
            path "/ncs:devices/ncs:device/ncs:config/ios:policy-map/name" {
              tailf:xpath-root 3;
            }
          }
        }
        leaf output {
          tailf:info
            "Assign policy-map to the output of an interface";
          type string {
            tailf:info
              "WORD;;Policy map name";
          }
          tailf:non-strict-leafref {
            path "/ncs:devices/ncs:device/ncs:config/ios:policy-map/name" {
              tailf:xpath-root 3;
            }
          }
        }
      }
    }
    leaf config-register {
      tailf:ncs-device-type "cli-ned";
      tailf:display-when "not(../../ncs:module) or ../../ncs:module[ncs:name='tailf-ned-cisco-ios']";
      tailf:info
        "Define the configuration register";
      type string {
        tailf:info
          "<0x0-0xFFFF>  Config register number";
        pattern '[0-9xXa-fA-F].*';
      }
    }
    container clock {
      tailf:ncs-device-type "cli-ned";
      tailf:display-when "not(../../ncs:module) or ../../ncs:module[ncs:name='tailf-ned-cisco-ios']";
      tailf:info
        "Configure time-of-day clock";
      container calendar-valid {
        tailf:info
          "Calendar time is authoritative";
        presence "true";
      }
      container summer-time {
        tailf:info
          "Configure summer (daylight savings) time";
        tailf:cli-compact-syntax;
        tailf:cli-sequence-commands {
          tailf:cli-reset-siblings;
        }
        leaf zone {
          tailf:cli-drop-node-name;
          tailf:cli-incomplete-command;
          tailf:cli-disallow-value "date|recurring";
          type string {
            tailf:info
              "WORD;;name of time zone in summer";
          }
        }
        choice summer-choice {
          case date-case {
            leaf date {
              tailf:info
                "Configure absolute summer time";
              type empty;
            }
          }
          case recurring-case {
            leaf recurring {
              tailf:info
                "Configure recurring summer time";
              type empty;
            }
            leaf start {
              tailf:cli-drop-node-name;
              tailf:cli-incomplete-command;
              type union {
                type uint8 {
                  tailf:info
                    "<1-4>;;Week number to start";
                  range "1..4";
                }
                type enumeration {
                  enum "first" {
                    tailf:info
                      "First week of the month";
                  }
                  enum "last" {
                    tailf:info
                      "Last week of the month";
                  }
                }
              }
            }
            leaf start-day {
              tailf:cli-drop-node-name;
              tailf:cli-incomplete-command;
              type weekday-type {
                tailf:info
                  "DAY;;Weekday to start";
              }
            }
            leaf start-month {
              tailf:cli-drop-node-name;
              tailf:cli-incomplete-command;
              type month-type {
                tailf:info
                  "MONTH;;Month to start";
              }
            }
            leaf start-time {
              tailf:cli-drop-node-name;
              tailf:cli-incomplete-command;
              type hhmm-type {
                tailf:info
                  "hh:mm;;Time to start (hh:mm)";
              }
            }
            leaf end {
              tailf:cli-drop-node-name;
              tailf:cli-incomplete-command;
              type union {
                type uint8 {
                  tailf:info
                    "<1-4>;;Week number to end";
                  range "1..4";
                }
                type enumeration {
                  enum "first" {
                    tailf:info
                      "First week of the month";
                  }
                  enum "last" {
                    tailf:info
                      "Last week of the month";
                  }
                }
              }
            }
            leaf end-day {
              tailf:cli-drop-node-name;
              tailf:cli-incomplete-command;
              type weekday-type {
                tailf:info
                  "DAY;;Weekday to end";
              }
            }
            leaf end-month {
              tailf:cli-drop-node-name;
              tailf:cli-incomplete-command;
              type month-type {
                tailf:info
                  "MONTH;;Month to end";
              }
            }
            leaf end-time {
              tailf:cli-drop-node-name;
              type hhmm-type {
                tailf:info
                  "hh:mm;;Time to end (hh:mm)";
              }
            }
          }
        }
      }
      container timezone {
        tailf:info
          "Configure time zone";
        tailf:cli-compact-syntax;
        tailf:cli-sequence-commands {
          tailf:cli-reset-siblings;
        }
        leaf zone {
          tailf:cli-drop-node-name;
          tailf:cli-incomplete-command;
          type string {
            tailf:info
              "WORD;;name of time zone";
          }
        }
        leaf offset {
          tailf:cli-drop-node-name;
          tailf:cli-optional-in-sequence;
          tailf:cli-incomplete-command;
          type enumeration {
            enum "+";
            enum "-";
          }
        }
        leaf hours {
          tailf:cli-drop-node-name;
          type int8 {
            tailf:info
              "<-23 - 23>;;Hours offset from UTC";
            range "-23..23";
          }
        }
        leaf minutes {
          tailf:cli-drop-node-name;
          type int8 {
            tailf:info
              "<0-59>;;Minutes ofset from UTC";
            range "0..59";
          }
        }
      }
    }
    container gatekeeper {
      tailf:ncs-device-type "cli-ned";
      tailf:display-when "not(../../ncs:module) or ../../ncs:module[ncs:name='tailf-ned-cisco-ios']";
      tailf:info
        "Enter gatekeeper configuration mode";
      tailf:cli-add-mode;
      tailf:cli-mode-name "config-gk";
      leaf shutdown {
        tailf:info
          "Shutdown Gatekeeper";
        type empty;
      }
    }
    container line {
      tailf:ncs-device-type "cli-ned";
      tailf:display-when "not(../../ncs:module) or ../../ncs:module[ncs:name='tailf-ned-cisco-ios']";
      tailf:info
        "Configure a terminal line";
      list aux {
        tailf:info
          "Auxiliary line";
        tailf:cli-full-command;
        tailf:cli-mode-name "config-line";
        key "first";
        max-elements 1;
        leaf first {
          type enumeration {
            enum "0" {
              tailf:info
                "<0-0>;;First Line number";
            }
          }
        }
        uses line-grouping;
      }
      list console {
        tailf:info
          "Primary terminal line";
        tailf:cli-full-command;
        tailf:cli-mode-name "config-line";
        tailf:cli-allow-key-abbreviation;
        key "first";
        max-elements 1;
        leaf first {
          type enumeration {
            enum "0" {
              tailf:info
                "<0-0>;;First Line number";
            }
          }
        }
        uses line-grouping;
      }
      container vty-single {
        tailf:cli-no-keyword;
        tailf:cli-drop-node-name;
        list vty {
          tailf:info
            "Virtual terminal";
          tailf:cli-full-command;
          tailf:cli-mode-name "config-line";
          key "first";
          leaf first {
            type uint16 {
              tailf:info
                "<0-1869>;;First Line number";
              range "0..1869";
            }
          }
          uses line-grouping;
        }
      }
      list vty {
        tailf:info
          "Virtual terminal";
        tailf:cli-full-command;
        tailf:cli-mode-name "config-line";
        key "first last";
        leaf first {
          type uint16 {
            tailf:info
              "<0-1869>;;First Line number";
            range "0..1869";
          }
        }
        leaf last {
          type uint16 {
            tailf:info
              "<1-1869>;;Last Line number";
            range "1..1869";
          }
        }
        uses line-grouping;
      }
    }
    container logging {
      tailf:ncs-device-type "cli-ned";
      tailf:display-when "not(../../ncs:module) or ../../ncs:module[ncs:name='tailf-ned-cisco-ios']";
      tailf:info
        "Modify message logging facilities";
      leaf alarm {
        tailf:info
          "Configure syslog for alarms";
        tailf:cli-full-command;
        type union {
          type uint8 {
            tailf:info
              "<1-4>;;Alarm Logging severity level";
            range "1..4";
          }
          type enumeration {
            enum "critical" {
              tailf:info
                "Service affecting Condition       (severity=1)";
            }
            enum "informational" {
              tailf:info
                "Informational messages            (severity=4)";
            }
            enum "major" {
              tailf:info
                "Immediate action needed           (severity=2)";
            }
            enum "minor" {
              tailf:info
                "Minor warning conditions          (severity=3)";
            }
          }
        }
      }
      container buffered {
        tailf:info
          "Set buffered logging parameters";
        leaf size {
          tailf:cli-drop-node-name;
          type uint32 {
            tailf:info
              "<4096-2147483647>;;Logging buffer size";
            range "4096..2147483647";
          }
        }
        leaf severity {
          tailf:cli-drop-node-name;
          tailf:cli-full-command;
          type logging-level-type;
        }
        leaf xxml {
          tailf:alt-name "xml";
          tailf:info
            "Enable logging in XML to XML logging buffer";
          tailf:cli-full-command;
          type uint32 {
            tailf:info
              "<4096-2147483647>;;XML logging buffer size";
            range "4096..2147483647";
          }
        }
      }
      leaf console {
        tailf:info
          "Set console logging parameters";
        type enumeration {
          enum "alerts" {
            tailf:info
              "Immediate action needed           (severity=1)";
          }
          enum "critical" {
            tailf:info
              "Critical conditions               (severity=2)";
          }
          enum "debugging" {
            tailf:info
              "Debugging messages                (severity=7)";
          }
          enum "discriminator" {
            tailf:info
              "Establish MD-Console association";
          }
          enum "emergencies" {
            tailf:info
              "System is unusable                (severity=0)";
          }
          enum "errors" {
            tailf:info
              "Error conditions                  (severity=3)";
          }
          enum "filtered" {
            tailf:info
              "Enable filtered logging";
          }
          enum "guaranteed" {
            tailf:info
              "Guarantee console messages";
          }
          enum "informational" {
            tailf:info
              "Informational messages            (severity=6)";
          }
          enum "notifications" {
            tailf:info
              "Normal but significant conditions (severity=5)";
          }
          enum "warnings" {
            tailf:info
              "Warning conditions                (severity=4)";
          }
          enum "xml" {
            tailf:info
              "Enable logging in XML";
          }
        }
      }
      container event {
        tailf:info
          "Global interface events";
        container link-status {
          tailf:info
            "Globally enable/disable link UPDOWN message";
          leaf boot {
            tailf:info
              "Supress/Allow link UPDOWN messages during boot";
            type empty;
          }
          leaf global {
            type empty;
          }
          leaf default {
            tailf:info
              "Link UPDOWN messages for all interfaces";
            type empty;
          }
        }
      }
      container esm {
        tailf:info
          "Set ESM filter restrictions";
        leaf config {
          tailf:info
            "Permit/Deny configuration changes from ESM filters";
          tailf:cli-full-command;
          type empty;
        }
      }
      leaf facility {
        tailf:info
          "Facility parameter for syslog messages";
        type enumeration {
          enum "auth" {
            tailf:info
              "Authorization system";
          }
          enum "cron" {
            tailf:info
              "Cron/at facility";
          }
          enum "daemon" {
            tailf:info
              "System daemons";
          }
          enum "kern" {
            tailf:info
              "Kernel";
          }
          enum "local0" {
            tailf:info
              "Local use";
          }
          enum "local1" {
            tailf:info
              "Local use";
          }
          enum "local2" {
            tailf:info
              "Local use";
          }
          enum "local3" {
            tailf:info
              "Local use";
          }
          enum "local4" {
            tailf:info
              "Local use";
          }
          enum "local5" {
            tailf:info
              "Local use";
          }
          enum "local6" {
            tailf:info
              "Local use";
          }
          enum "local7" {
            tailf:info
              "Local use";
          }
          enum "lpr" {
            tailf:info
              "Line printer system";
          }
          enum "mail" {
            tailf:info
              "Mail system";
          }
          enum "news" {
            tailf:info
              "USENET news";
          }
          enum "sys10" {
            tailf:info
              "System use";
          }
          enum "sys11" {
            tailf:info
              "System use";
          }
          enum "sys12" {
            tailf:info
              "System use";
          }
          enum "sys13" {
            tailf:info
              "System use";
          }
          enum "sys14" {
            tailf:info
              "System use";
          }
          enum "sys9" {
            tailf:info
              "System use";
          }
          enum "syslog" {
            tailf:info
              "Syslog itself";
          }
          enum "user" {
            tailf:info
              "User process";
          }
          enum "uucp" {
            tailf:info
              "Unix-to-Unix copy system";
          }
        }
      }
      container history {
        tailf:info
          "Configure syslog history table";
        leaf size {
          tailf:info
            "Set history table size";
          type uint16 {
            tailf:info
              "<0-500>;History size";
          }
        }
        leaf severity-level {
          tailf:cli-drop-node-name;
          type union {
            type uint8 {
              tailf:info
                "<0-7>;;Logging severity level";
              range "0..7";
            }
            type enumeration {
              enum "alerts" {
                tailf:info
                  "Immediate action needed           (severity=1)";
              }
              enum "critical" {
                tailf:info
                  "Critical conditions               (severity=2)";
              }
              enum "debugging" {
                tailf:info
                  "Debugging messages                (severity=7)";
              }
              enum "emergencies" {
                tailf:info
                  "System is unusable                (severity=0)";
              }
              enum "errors" {
                tailf:info
                  "Error conditions                  (severity=3)";
              }
              enum "informational" {
                tailf:info
                  "Informational messages            (severity=6)";
              }
              enum "notifications" {
                tailf:info
                  "Normal but significant conditions (severity=5)";
              }
              enum "warnings" {
                tailf:info
                  "Warning conditions                (severity=4)";
              }
            }
          }
        }
      }
      list hostname {
        tailf:info
          "Hostname or A.B.C.D;;IP address of the logging host";
        tailf:cli-drop-node-name;
        tailf:cli-suppress-mode;
        tailf:cli-delete-when-empty;
        key "host";
        leaf host {
          tailf:cli-disallow-value "esm|alarm|buffered|facility|history|rate-limit|source-interface|host|console";
          tailf:cli-full-command;
          type inet:host {
            tailf:info
              "Hostname or A.B.C.D";
          }
        }
      }
      list host {
        tailf:info
          "Set syslog server IP address and parameters";
        tailf:cli-suppress-mode;
        tailf:cli-delete-when-empty;
        tailf:cli-compact-syntax;
        key "host";
        leaf host {
          tailf:cli-disallow-value "esm|alarm|buffered|facility|history|rate-limit|source-interface|host";
          tailf:cli-full-command;
          type inet:host {
            tailf:info
              "Hostname or A.B.C.D";
          }
        }
        leaf vrf {
          tailf:info
            "Set VRF option";
          type string {
            tailf:info
              "WORD;;VPN Routing/Forwarding instance name";
          }
        }
        leaf discriminator {
          tailf:info
            "Specify a message discriminator identifier for this logging session";
          type string {
            tailf:info
              "WORD;;Message discriminator identifier for this logging session (8 chars. max)";
          }
        }
      }
      container rate-limit {
        tailf:info
          "Set messages per second limit";
        tailf:cli-sequence-commands;
        tailf:cli-compact-syntax;
        tailf:cli-reset-container;
        leaf console {
          tailf:info
            "Rate limit only console messages";
          tailf:cli-optional-in-sequence;
          tailf:cli-incomplete-command;
          type empty;
        }
        leaf all {
          tailf:info
            "Rate limit all messages, including debug messages";
          tailf:cli-optional-in-sequence;
          tailf:cli-incomplete-command;
          type empty;
        }
        leaf rate {
          tailf:cli-drop-node-name;
          type uint16 {
            tailf:info
              "<1-10000>;;Messages per second";
          }
        }
      }
      container source-interface {
        tailf:info
          "Specify interface for source address in logging transactions";
        tailf:cli-diff-dependency "/ios:interface" {
          tailf:xpath-root 3;
        }
        uses interface-grouping;
      }
      leaf trap {
        tailf:info
          "Set syslog server logging level";
        tailf:cli-full-command;
        type logging-level-type;
      }
    }
    container mgcp {
      tailf:ncs-device-type "cli-ned";
      tailf:display-when "not(../../ncs:module) or ../../ncs:module[ncs:name='tailf-ned-cisco-ios']";
      tailf:info
        "Enable Media Gateway Control Protocol";
      container fax {
        tailf:info
          "Configure MGCP Fax Parameters";
        container t38 {
          tailf:info
            "Configure MGCP Fax T.38 Parameters";
          leaf ecm {
            tailf:info
              "Enable Error Correction Mode (ECM)";
            tailf:cli-full-command;
            type empty;
          }
        }
      }
      container profile {
        tailf:info
          "MGCP profile configuration mode";
        leaf default {
          tailf:info
            "Configure MGCP default profile";
          type empty;
        }
      }
    }
    container multilink {
      tailf:ncs-device-type "cli-ned";
      tailf:display-when "not(../../ncs:module) or ../../ncs:module[ncs:name='tailf-ned-cisco-ios']";
      tailf:info
        "PPP multilink global configuration";
      leaf bundle-name {
        tailf:info
          "Select method for naming multilink bundles";
        tailf:cli-full-command;
        type enumeration {
          enum "authenticated" {
            tailf:info
              "Use peer's authenticated name";
          }
          enum "both" {
            tailf:info
              "Use peer's authenticated name and endpoint discriminator";
          }
          enum "endpoint" {
            tailf:info
              "Use peer's endpoint discriminator";
          }
          enum "rfc" {
            tailf:info
              "Use peer and local authenticated name and endpoint discriminator";
          }
        }
      }
      leaf virtual-template {
        tailf:info
          "virtual-template interface";
        tailf:cli-full-command;
        type uint16 {
          tailf:info
            "<1-4095>;;virtual template number";
          range "1..4095";
        }
      }
    }
    container ntp {
      tailf:ncs-device-type "cli-ned";
      tailf:display-when "not(../../ncs:module) or ../../ncs:module[ncs:name='tailf-ned-cisco-ios']";
      tailf:info
        "Configure NTP";
      tailf:cli-diff-dependency "/ios:interface" {
        tailf:xpath-root 3;
      }
      container access-group {
        tailf:info
          "Control NTP access";
        leaf peer {
          tailf:info
            "Provide full access";
          type union {
            type uint16 {
              tailf:info
                "<1-99>;;Standard IP access list";
              range "1..99";
            }
            type uint16 {
              tailf:info
                "<1300-1999>;;Standard IP access list (expanded range)";
              range "1300..1999";
            }
          }
        }
        leaf serve {
          tailf:info
            "Provide server and query access";
          type union {
            type uint16 {
              tailf:info
                "<1-99>;;Standard IP access list";
              range "1..99";
            }
            type uint16 {
              tailf:info
                "<1300-1999>;;Standard IP access list (expanded range)";
              range "1300..1999";
            }
          }
        }
      }
      container server {
        tailf:info
          "Configure NTP server";
        uses ntp-server-grouping;
        list vrf {
          tailf:info
            "VPN Routing/Forwarding Information";
          tailf:cli-suppress-mode;
          tailf:cli-delete-when-empty;
          tailf:cli-compact-syntax;
          tailf:cli-reset-container;
          tailf:cli-incomplete-command;
          tailf:cli-diff-dependency "/ios:vrf/definition" {
            tailf:xpath-root 3;
          }
          tailf:cli-diff-dependency "/ios:ip/vrf" {
            tailf:xpath-root 3;
          }
          key "name";
          leaf name {
            type string {
              tailf:info
                "WORD;;VPN Routing/Forwarding instance name";
            }
          }
          uses ntp-server-grouping;
        }
      }
      container source {
        tailf:info
          "Configure interface for source address";
        uses interface-grouping;
      }
      leaf update-calendar {
        tailf:info
          "Periodically update calendar with NTP time";
        type empty;
      }
    }
    container no {
      tailf:ncs-device-type "cli-ned";
      tailf:display-when "not(../../ncs:module) or ../../ncs:module[ncs:name='tailf-ned-cisco-ios']";
      container mac-address-table {
        tailf:info
          "Configure the MAC address table";
        container learning {
          tailf:info
            "Enable a MAC table learning feature";
          list vlan {
            tailf:info
              "Layer 2 table learning per VLAN";
            tailf:cli-suppress-mode;
            tailf:cli-delete-when-empty;
            key "id";
            leaf id {
              type uint16 {
                tailf:info
                  "<1-4094>;;VLAN ID";
                range "1..4094";
              }
            }
            leaf module {
              tailf:info
                "Layer 2 table learning per VLAN per module";
              type uint8 {
                tailf:info
                  "<1-9>;;Module";
                range "1..9";
              }
            }
          }
        }
      }
    }
    container privilege {
      tailf:ncs-device-type "cli-ned";
      tailf:display-when "not(../../ncs:module) or ../../ncs:module[ncs:name='tailf-ned-cisco-ios']";
      tailf:info
        "Command privilege parameters";
      container exec {
        tailf:info
          "Exec mode";
        list level {
          tailf:info
            "Set privilege level of command";
          tailf:cli-suppress-mode;
          tailf:cli-delete-when-empty;
          tailf:cli-compact-syntax;
          tailf:cli-incomplete-command;
          tailf:cli-no-key-completion;
          key "privilege";
          leaf privilege {
            tailf:cli-incomplete-command;
            tailf:cli-incomplete-no;
            tailf:cli-suppress-range;
            type uint8 {
              tailf:info
                "<0-15>;;Privilege level";
            }
          }
          list command-list {
            tailf:cli-suppress-mode;
            tailf:cli-delete-when-empty;
            tailf:cli-drop-node-name;
            tailf:cli-compact-syntax;
            tailf:cli-show-long-obu-diffs;
            tailf:cli-no-key-completion;
            tailf:cli-suppress-key-abbreviation;
            tailf:cli-no-match-completion;
            ordered-by user;
            key "command";
            leaf command {
              tailf:cli-drop-node-name;
              tailf:cli-multi-word-key;
              type string {
                tailf:info
                  "LINE;;Initial keywords of the command to modify";
                pattern '(show.*)|(write.*)';
              }
            }
          }
        }
      }
    }
    container redundancy {
      tailf:ncs-device-type "cli-ned";
      tailf:display-when "not(../../ncs:module) or ../../ncs:module[ncs:name='tailf-ned-cisco-ios']";
      tailf:info
        "Enter redundancy mode";
      tailf:cli-add-mode;
      tailf:cli-mode-name "config-red";
      leaf maintenance-mode {
        tailf:info
          "Enable/Disable maintenance mode ";
        type empty;
      }
      container main-cpu {
        tailf:info
          "Enter main-cpu mode";
        tailf:cli-add-mode;
        container auto-sync {
          leaf running-config {
            type empty;
          }
          leaf config-register {
            type empty;
          }
          leaf bootvar {
            type empty;
          }
        }
      }
      leaf mode {
        tailf:info
          "redundancy mode for this chassis";
        type enumeration {
          enum "rpr" {
            tailf:info
              "Route Processor Redundancy";
          }
          enum "rpr-plus" {
            tailf:info
              "Route Processor Redundancy Plus";
          }
          enum "sso" {
            tailf:info
              "Stateful Switchover";
          }
          enum "none" {
            tailf:info
              "None";
          }
        }
      }
    }
    container scheduler {
      tailf:ncs-device-type "cli-ned";
      tailf:display-when "not(../../ncs:module) or ../../ncs:module[ncs:name='tailf-ned-cisco-ios']";
      tailf:info
        "Scheduler parameters";
      container allocate {
        tailf:cli-sequence-commands;
        tailf:cli-compact-syntax;
        tailf:info
          "Guarantee CPU time for processes";
        leaf interrupt-time {
          tailf:cli-drop-node-name;
          tailf:cli-incomplete-command;
          type uint16 {
            tailf:info
              "<400-60000>;;Microseconds handling network interrupts";
            range "400..60000";
          }
        }
        leaf process-time {
          tailf:cli-drop-node-name;
          type uint16 {
            tailf:info
              "<100-4000>;;Microseconds running processes";
            range "100..4000";
          }
        }
      }
    }
    container spanning-tree {
      tailf:ncs-device-type "cli-ned";
      tailf:display-when "not(../../ncs:module) or ../../ncs:module[ncs:name='tailf-ned-cisco-ios']";
      tailf:info
        "Spanning Tree Subsystem";
      container etherchannel {
        tailf:info
          "Spanning tree etherchannel specific configuration";
        container guard {
          tailf:info
            "Configure guard features for etherchannel";
          leaf misconfig {
            tailf:info
              "Enable guard to protect against etherchannel misconfiguration";
            type empty;
          }
        }
      }
      container extend {
        tailf:info
          "Spanning Tree 802.1t extensions";
        leaf system-id {
          tailf:info
            "Extend system-id into priority portion of the bridge id (PVST & Rapid PVST only)";
          type empty;
        }
      }
      container loopguard {
        tailf:info
          "Spanning tree loopguard options";
        leaf default {
          tailf:info
            "Enable loopguard by default on all ports";
          type empty;
        }
      }
      container mst {
        tailf:info
          "Multiple spanning tree configuration";
        list instance-range {
          tailf:cli-suppress-mode;
          tailf:cli-delete-when-empty;
          tailf:cli-drop-node-name;
          tailf:cli-compact-syntax;
          tailf:cli-range-list-syntax;
          key "id";
          leaf id {
            type uint16;
          }
          leaf priority {
            tailf:info
              "Set the bridge priority for the spanning tree";
            type uint16 {
              tailf:info
                "<0-61440>;;bridge priority in increments of 4096";
              range "0..61440";
            }
          }
        }
        container configuration {
          tailf:info
            "Enter MST configuration submode";
          tailf:cli-add-mode;
          tailf:cli-mode-name "config-mst";
          leaf name {
            tailf:info
              "Set configuration name";
            type string {
              tailf:info
                "WORD;;Configuration name";
            }
          }
          list instance {
            tailf:info
              "Map vlans to an MST instance";
            tailf:cli-suppress-mode;
            tailf:cli-delete-when-empty;
            key "id";
            leaf id {
              type uint16 {
                tailf:info
                  "<0-4094>;;MST instance id";
                range "0..4094";
              }
            }
            leaf-list vlan {
              tailf:info
                "Range of vlans to add to the instance mapping";
              tailf:cli-range-list-syntax;
              type uint16 {
                tailf:info
                  "LINE;;vlan range ex: 1-65, 72, 300 -200";
              }
            }
          }
        }
      }
      container optimize {
        container bpdu {
          leaf transmission {
            tailf:cli-boolean-no;
            tailf:cli-show-no;
            type boolean;
          }
        }
      }
      container portfast {
        tailf:info
          "Spanning tree portfast options";
        tailf:cli-compact-syntax;
        tailf:cli-sequence-commands {
          tailf:cli-reset-siblings;
        }
        leaf bdpu {
          tailf:cli-drop-node-name;
          tailf:cli-optional-in-sequence;
          type enumeration {
            enum "bpdufilter" {
              tailf:info
                "Enable portfast bdpu filter on this switch";
            }
            enum "bpduguard" {
              tailf:info
                "Enable portfast bpdu guard on this switch";
            }
          }
        }
        leaf default {
          tailf:info
            "Enable portfast by default on all access ports";
          type empty;
        }
      }
      leaf mode {
        tailf:info
          "Spanning tree operating mode";
        tailf:cli-show-with-default;
        tailf:cli-full-command;
        type enumeration {
          enum "mst" {
            tailf:info
              "Multiple spanning tree mode";
          }
          enum "pvst" {
            tailf:info
              "Per-Vlan spanning tree mode";
          }
          enum "rapid-pvst" {
            tailf:info
              "Per-Vlan rapid spanning tree mode";
          }
        }
      }
      container vlans-max-age {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf max-age {
            tailf:info
              "Set the max age interval for the spanning tree";
            type uint8 {
              tailf:info
                "<6-40>;;maximum number of seconds the information in a BPDU is valid";
              range "6..40";
            }
          }
        }
      }
      container vlans-forward-time {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf forward-time {
            tailf:info
              "Set the forward delay for the spanning tree";
            type uint8 {
              tailf:info
                "<4-30>;;number of seconds for the forward delay timer";
              range "4..30";
            }
          }
        }
      }
      container vlans-hello-time {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf hello-time {
            tailf:info
              "Set the hello interval for the spanning tree";
            type uint8 {
              tailf:info
                "<1-10>;;number of seconds between generation of config BPDUs";
              range "1..10";
            }
          }
        }
      }
      container vlans-priority {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          leaf priority {
            tailf:info
              "Set the bridge priority for the spanning tree";
            type uint16 {
              tailf:info
                "<0-61440>;;bridge priority in increments of 4096";
              range "0..61440";
            }
          }
        }
      }
      container vlans-root {
        tailf:cli-drop-node-name;
        list vlan {
          tailf:info
            "VLAN Switch Spanning Tree";
          tailf:cli-range-list-syntax;
          tailf:cli-suppress-mode;
          tailf:cli-delete-when-empty;
          key "id";
          leaf id {
            type uint16 {
              tailf:info
                "WORD;;vlan range, example: 1,3-5,7,9-11";
              range "1..4096";
            }
          }
          container root {
            tailf:info
              "Configure switch as root";
            container primary {
              tailf:info
                "Configure this switch as primary root for this spanning tree";
              tailf:cli-compact-syntax;
              tailf:cli-sequence-commands {
                tailf:cli-reset-siblings;
              }
              leaf diameter {
                tailf:info
                  "Network diameter of this spanning tree";
                type uint8 {
                  tailf:info
                    "<2-7>;;Maximum number of bridges between any two end nodes";
                  range "2..7";
                }
              }
              leaf hello-time {
                tailf:info
                  "Hello interval for this spanning tree";
                type uint8 {
                  tailf:info
                    "<1-10>;;Hello interval in seconds";
                  range "1..10";
                }
              }
            }
            container secondary {
              tailf:info
                "Configure switch as secondary root";
              tailf:cli-compact-syntax;
              tailf:cli-sequence-commands {
                tailf:cli-reset-siblings;
              }
              leaf diameter {
                tailf:info
                  "Network diameter of this spanning tree";
                type uint8 {
                  tailf:info
                    "<2-7>;;Maximum number of bridges between any two end nodes";
                  range "2..7";
                }
              }
              leaf hello-time {
                tailf:info
                  "Hello interval for this spanning tree";
                type uint8 {
                  tailf:info
                    "<1-10>;;Hello interval in seconds";
                  range "1..10";
                }
              }
            }
          }
        }
      }
    }
    container dot1x {
      tailf:ncs-device-type "cli-ned";
      tailf:display-when "not(../../ncs:module) or ../../ncs:module[ncs:name='tailf-ned-cisco-ios']";
      tailf:info
        "IEEE 802.1X Global Configuration Commands";
      container critical {
        tailf:info
          "Set 802.1x Critical Authentication parameters";
        leaf eapol {
          tailf:info
            "Send EAPOL-Success on successful Critical Authentication";
          type empty;
        }
        container recovery {
          tailf:info
            "Set 802.1x Critical Authentication Recovery parameters";
          leaf delay {
            tailf:info
              "Set 802.1x Critical Authentication Recovery Delay period";
            type uint16 {
              tailf:info
                "<1-10000>;;802.1x Critical Authentication Recovery delay in milliseconds";
              range "1..10000";
            }
          }
        }
      }
      leaf system-auth-control {
        tailf:info
          "Enable or Disable SysAuthControl";
        type empty;
      }
    }
    container power {
      tailf:ncs-device-type "cli-ned";
      tailf:display-when "not(../../ncs:module) or ../../ncs:module[ncs:name='tailf-ned-cisco-ios']";
      tailf:info
        "Power configure";
      leaf redundancy-mode {
        tailf:info
          "set power supply redundancy mode";
        type enumeration {
          enum "combined" {
            tailf:info
              "combine power supply outputs (no redundancy)";
          }
          enum "redundant" {
            tailf:info
              "either power supply can operate system (redundancy)";
          }
        }
      }
    }
    container parameter-map {
      tailf:ncs-device-type "cli-ned";
      tailf:display-when "not(../../ncs:module) or ../../ncs:module[ncs:name='tailf-ned-cisco-ios']";
      tailf:info
        "parameter map";
      container type {
        tailf:info
          "parameter map type";
        list inspect {
          tailf:info
            "inspect parameter-map";
          key "id";
          leaf id {
            type string {
              tailf:info
                "WORD;;parameter-map name";
            }
          }
          leaf alert {
            tailf:info
              "Turn on/off alert";
            type enumeration {
              enum "off" {
                tailf:info
                  "Turn off alert";
              }
              enum "on" {
                tailf:info
                  "Turn on alert";
              }
            }
          }
          leaf audit-trail {
            tailf:info
              "Turn on/off audit trail";
            type enumeration {
              enum "off" {
                tailf:info
                  "Turn off audit trail";
              }
              enum "on" {
                tailf:info
                  "Turn on audit trail";
              }
            }
          }
          leaf dns-timeout {
            tailf:info
              "Specify timeout for DNS";
            type uint32 {
              tailf:info
                "<1-2147483>;;Timeout in seconds";
              range "1..2147483";
            }
          }
          container icmp {
            tailf:info
              "Config timeout values for icmp";
            leaf idle-time {
              tailf:info
                "Specify timeout for icmp";
              type uint32 {
                tailf:info
                  "<1-2147483>;;Timeout in seconds";
                range "1..2147483";
              }
            }
          }
          container max-incomplete {
            tailf:info
              "Specify maximum number of incomplete connections before clamping";
            leaf high {
              tailf:info
                "Specify high-watermark for clamping";
              type uint32 {
                tailf:info
                  "<1-2147483647>;;Number of connections";
                range "1..2147483647";
              }
            }
            leaf low {
              tailf:info
                "Specify low-watermark for clamping";
              type uint32 {
                tailf:info
                  "<1-2147483647>;;Number of connections";
                range "1..2147483647";
              }
            }
          }
          container one-minute {
            tailf:info
              "Specify one-minute-sample watermarks for clamping";
            leaf high {
              tailf:info
                "Specify high-watermark for clamping";
              type uint32 {
                tailf:info
                  "<1-2147483647>;;Number of connections";
                range "1..2147483647";
              }
            }
            leaf low {
              tailf:info
                "Specify low-watermark for clamping";
              type uint32 {
                tailf:info
                  "<1-2147483647>;;Number of connections";
                range "1..2147483647";
              }
            }
          }
          container sessions {
            tailf:info
              "Maximum number of inspect sessions";
            leaf maximum {
              tailf:info
                "Maximum sessions";
              type uint32 {
                tailf:info
                  "<1-2147483647>;;Number of sessions";
                range "1..2147483647";
              }
            }
          }
          container tcp {
            tailf:info
              "Config timeout values for tcp connections";
            leaf finwait-time {
              tailf:info
                "Specify timeout for TCP connections after a FIN";
              type uint32 {
                tailf:info
                  "<1-2147483>;;Timeout in seconds";
                range "1..2147483";
              }
            }
            leaf idle-time {
              tailf:info
                "Specify idle timeout for tcp connections";
              type uint32 {
                tailf:info
                  "<1-2147483>;;Timeout in seconds";
                range "1..2147483";
              }
            }
            container max-incomplete {
              tailf:info
                "Specify max half-open connection per host";
              leaf host {
                tailf:info
                  "Specify max half-open connection per host";
                type uint32 {
                  tailf:info
                    "<1-4294967295>;;half-open sessions";
                  range "1..4294967295";
                }
              }
            }
            leaf synwait-time {
              tailf:info
                "Specify timeout for TCP connections after a SYN and no";
              type uint32 {
                tailf:info
                  "<1-2147483>;;Timeout in seconds";
                range "1..2147483";
              }
            }
          }
          container udp {
            tailf:info
              "Config timeout values for udp flows";
            leaf idle-time {
              tailf:info
                "Specify idle timeout for udp";
              type uint32 {
                tailf:info
                  "<1-2147483>;;Timeout in seconds";
                range "1..2147483";
              }
            }
          }
        }
      }
    }
    container vpdn {
      tailf:ncs-device-type "cli-ned";
      tailf:display-when "not(../../ncs:module) or ../../ncs:module[ncs:name='tailf-ned-cisco-ios']";
      tailf:info
        "Virtual Private Dialup Network";
      leaf authen-before-forward {
        tailf:info
          "Authenticate a user locally before tunnelling";
        type empty;
      }
      leaf enable {
        tailf:info
          "Enable VPDN";
        type empty;
      }
      leaf-list search-order {
        ordered-by user;
        tailf:info
          "Configure the order to search different VPDN tunnel types";
        type enumeration {
          enum "dnis" {
            tailf:info
              "Tunnel based on DNIS";
          }
          enum "domain" {
            tailf:info
              "Tunnel based on domain";
          }
          enum "multihop-hostname" {
            tailf:info
              "Tunnel based on peer hostname from ingress tunnel";
          }
        }
      }
    }
    container bba-group {
      tailf:ncs-device-type "cli-ned";
      tailf:display-when "not(../../ncs:module) or ../../ncs:module[ncs:name='tailf-ned-cisco-ios']";
      tailf:info
        "Configure BBA Group";
      list pppoe {
        tailf:info
          "PPPoE type";
        key "id";
        leaf id {
          type union {
            type string {
              tailf:info
                "WORD;;BBA Group name";
            }
            type enumeration {
              enum "global" {
                tailf:info
                  "PPPoE global group";
              }
            }
          }
        }
        container vendor-tag {
          tailf:info
            "PPPoE Vendor Specific Tag";
          container circuit-id {
            tailf:info
              "Circuit-Id";
            leaf service {
              tailf:info
                "Enable processing";
              type empty;
            }
          }
          container dsl-sync-rate {
            tailf:info
              "DSL-Sync-Rate";
            leaf service {
              tailf:info
                "Enable processing";
              type empty;
            }
          }
          container remote-id {
            tailf:info
              "Remote-Id";
            leaf service {
              tailf:info
                "Enable processing";
              type empty;
            }
          }
          leaf strip {
            tailf:info
              "Strip all vendor tags";
            type empty;
          }
        }
        leaf virtual-template {
          tailf:info
            "BBA virtual template command";
          type uint16 {
            tailf:info
              "<1-4095>;;Virtual Template interface number";
            range "1..4095";
          }
        }
      }
    }
    container mac {
      tailf:ncs-device-type "cli-ned";
      tailf:display-when "not(../../ncs:module) or ../../ncs:module[ncs:name='tailf-ned-cisco-ios']";
      tailf:info
        "Global MAC configuration subcommands";
      container access-list {
        tailf:info
          "Named access-list";
        list extended {
          tailf:info
            "Extended Access List";
          key "id";
          leaf id {
            type string {
              tailf:info
                "WORD;;access-list name";
            }
          }
          container deny {
            tailf:info
              "Specify packets to reject";
            tailf:cli-compact-syntax;
            tailf:cli-sequence-commands;
            container source {
              tailf:cli-compact-syntax;
              tailf:cli-flatten-container;
              tailf:cli-drop-node-name;
              choice target-choice {
                leaf any {
                  tailf:info
                    "any source MAC address";
                  type empty;
                }
                leaf host {
                  tailf:info
                    "A single source host";
                  type string {
                    tailf:info
                      "H.H.H;;48-bit source MAC address";
                  }
                }
              }
            }
            container dest {
              tailf:cli-compact-syntax;
              tailf:cli-flatten-container;
              tailf:cli-drop-node-name;
              choice target-choice {
                leaf any {
                  tailf:info
                    "any destination MAC address";
                  type empty;
                }
                leaf host {
                  tailf:info
                    "A single destination host";
                  type string {
                    tailf:info
                      "H.H.H;;48-bit destination MAC address";
                  }
                }
              }
            }
          }
          container permit {
            tailf:info
              "Specify packets to forward";
            tailf:cli-compact-syntax;
            tailf:cli-sequence-commands;
            container source {
              tailf:cli-compact-syntax;
              tailf:cli-flatten-container;
              tailf:cli-drop-node-name;
              choice target-choice {
                leaf any {
                  tailf:info
                    "any source MAC address";
                  type empty;
                }
                leaf host {
                  tailf:info
                    "A single source host";
                  type string {
                    tailf:info
                      "H.H.H;;48-bit source MAC address";
                  }
                }
              }
            }
            container dest {
              tailf:cli-compact-syntax;
              tailf:cli-flatten-container;
              tailf:cli-drop-node-name;
              choice target-choice {
                leaf any {
                  tailf:info
                    "any destination MAC address";
                  type empty;
                }
                leaf host {
                  tailf:info
                    "A single destination host";
                  type string {
                    tailf:info
                      "H.H.H;;48-bit destination MAC address";
                  }
                }
              }
            }
          }
        }
      }
    }
    container tacacs-server {
      tailf:ncs-device-type "cli-ned";
      tailf:display-when "not(../../ncs:module) or ../../ncs:module[ncs:name='tailf-ned-cisco-ios']";
      tailf:info
        "Modify TACACS query parameters";
      list host {
        tailf:info
          "Specify a TACACS server";
        tailf:cli-suppress-mode;
        tailf:cli-delete-when-empty;
        tailf:cli-compact-syntax;
        tailf:cli-reset-container;
        key "name";
        leaf name {
          type host-type {
            tailf:info
              "Hostname or A.B.C.D;;IP address of TACACS server";
          }
        }
        leaf port {
          tailf:info
            "TCP port for TACACS+ server (default is 49)";
          type uint16 {
            tailf:info
              "<1-65535>;;Port number";
            range "1..65535";
          }
        }
        leaf timeout {
          tailf:info
            "Time to wait for this TACACS server to reply (overrides default)";
          type uint16 {
            tailf:info
              "<1-1000>;;Timeout value in seconds to wait for server to reply";
            range "1..1000";
          }
        }
      }
      leaf timeout {
        tailf:info
          "Time to wait for a TACACS server to reply";
        type uint16 {
          tailf:info
            "<1-1000>;;Wait time (default 5 seconds)";
          range "1..1000";
        }
        default "5";
      }
      container directed-request {
        tailf:info
          "Allow user to specify tacacs server to use with `@server'";
        tailf:cli-compact-syntax;
        tailf:cli-sequence-commands;
        presence "true";
        leaf restricted {
          tailf:info
            "restrict queries to directed request servers only";
          tailf:cli-optional-in-sequence;
          type empty;
        }
        leaf no-truncate {
          tailf:info
            "Do not truncate the @hostname from username.";
          type empty;
        }
      }
      container key {
        tailf:info
          "Set TACACS+ encryption key.";
        tailf:cli-compact-syntax;
        tailf:cli-sequence-commands;
        leaf encryption {
          tailf:cli-drop-node-name;
          tailf:cli-incomplete-command;
          tailf:cli-optional-in-sequence;
          type enumeration {
            enum "0" {
              tailf:info
                "Specifies an UNENCRYPTED key will follow";
            }
            enum "7" {
              tailf:info
                "Specifies HIDDEN key will follow";
            }
          }
        }
        leaf key {
          tailf:cli-drop-node-name;
          tailf:cli-full-command;
          tailf:cli-multi-value;
          type string {
            tailf:info
              "LINE;;The UNENCRYPTED (cleartext) shared key";
          }
        }
      }
    }
    container upgrade {
      tailf:ncs-device-type "cli-ned";
      tailf:display-when "not(../../ncs:module) or ../../ncs:module[ncs:name='tailf-ned-cisco-ios']";
      tailf:info
        "Global upgrade configuration subcommands";
      container fpd {
        tailf:info
          "Configure field programmable devices upgrade options";
        leaf auto {
          tailf:info
            "Auto upgrade all FPD images";
          type empty;
        }
        leaf path {
          tailf:info
            "Set path to locate the FPD image package file for auto upgrade";
          type string;
        }
      }
    }
    container vtp {
      tailf:ncs-device-type "cli-ned";
      tailf:display-when "not(../../ncs:module) or ../../ncs:module[ncs:name='tailf-ned-cisco-ios']";
      tailf:info
        "Configure global VTP state";
      leaf file {
        tailf:info
          "Configure IFS filesystem file where VTP configuration is stored.";
        type string {
          tailf:info
            "WORD;;The ascii name of the IFS filesystem file where VTP configuration is stored.";
        }
      }
      leaf interface {
        tailf:info
          "Configure interface as the preferred source for the VTP IP updater address.";
        type string {
          tailf:info
            "WORD;;The name of the interface providing the VTP updater ID for this device.";
        }
      }
      leaf password {
        tailf:info
          "Set the password for the VTP administrative domain";
        type string {
          tailf:info
            "WORD;;The ascii password for the VTP administrative domain.";
        }
      }
      leaf pruning {
        tailf:info
          "Set the adminstrative domain to permit pruning";
        type empty;
      }
      leaf version {
        tailf:info
          "Set the adminstrative domain to VTP version";
        type uint8 {
          tailf:info
            "<1-3>;;Set the adminstrative domain VTP version number";
          range "1..3";
        }
      }
      leaf domain {
        tailf:info
          "Set the name of the VTP administrative domain.";
        type string;
      }
      leaf mode {
        tailf:info
          "Configure VTP device mode";
        type enumeration {
          enum "client" {
            tailf:info
              "Set the device to client mode.";
          }
          enum "off" {
            tailf:info
              "Set the device to off mode.";
          }
          enum "server" {
            tailf:info
              "Set the device to server mode.";
          }
          enum "transparent" {
            tailf:info
              "Set the device to transparent mode.";
          }
        }
      }
    }
    container rep {
      tailf:ncs-device-type "cli-ned";
      tailf:display-when "not(../../ncs:module) or ../../ncs:module[ncs:name='tailf-ned-cisco-ios']";
      tailf:info
        "Resilient Ethernet Protocol characteristics";
      container admin {
        tailf:info
          "administrative configuration";
        list vlan {
          tailf:info
            "VLAN";
          key "name";
          leaf name {
            type uint16 {
              tailf:info
                "<2-4094>;;between 2 and 4094";
              range "2..4094";
            }
          }
        }
      }
    }
    container xconnect {
      tailf:ncs-device-type "cli-ned";
      tailf:display-when "not(../../ncs:module) or ../../ncs:module[ncs:name='tailf-ned-cisco-ios']";
      container logging {
        container pseudowire {
          leaf status {
            tailf:cli-full-command;
            type empty;
          }
        }
        leaf redundancy {
          tailf:cli-full-command;
          type empty;
        }
      }
    }
    container fabric {
      tailf:ncs-device-type "cli-ned";
      tailf:display-when "not(../../ncs:module) or ../../ncs:module[ncs:name='tailf-ned-cisco-ios']";
      tailf:info
        "Catalyst 6000 crossbar fabric configuration commands";
      container switching-mode {
        tailf:info
          "Switching mode settings";
        container allow {
          tailf:info
            "Allow settings";
          choice allow-choice {
            leaf bus-mode {
              tailf:info
                "Allow switching in bus mode for modules";
              type empty;
            }
            container truncated {
              tailf:info
                "Truncated switching mode";
              presence "true";
              leaf threshold {
                tailf:info
                  "Number of SFM-capable modules for truncated switching mode. Switch applies the threshold only when the mode is disallowed. Switch ignores the threshold when the truncated mode is allowed";
                type uint8 {
                  tailf:info
                    "<1-9>;;Threshold for truncated switching mode.";
                  range "1..9";
                }
              }
            }
          }
        }
        container force {
          tailf:info
            "Force modules to different switching modes";
          leaf bus-mode {
            tailf:info
              "Switching mode of service modules will be forced to bus-mode by powercycling it.";
            type empty;
          }
        }
      }
    }
    container port-channel {
      tailf:ncs-device-type "cli-ned";
      tailf:display-when "not(../../ncs:module) or ../../ncs:module[ncs:name='tailf-ned-cisco-ios']";
      tailf:info
        "EtherChannel configuration";
      leaf load-balance {
        tailf:info
          "Load Balancing method";
        type enumeration {
          enum "dst-ip" {
            tailf:info
              "Dst IP Addr";
          }
          enum "dst-mac" {
            tailf:info
              "Dst Mac Addr";
          }
          enum "dst-mixed-ip-port" {
            tailf:info
              "Dst IP Addr and TCP/UDP Port";
          }
          enum "dst-port" {
            tailf:info
              "Dst TCP/UDP Port";
          }
          enum "mpls" {
            tailf:info
              "Load Balancing for MPLS packets";
          }
          enum "src-dst-ip" {
            tailf:info
              "Src XOR Dst IP Addr";
          }
          enum "src-dst-mac" {
            tailf:info
              "Src XOR Dst Mac Addr";
          }
          enum "src-dst-mixed-ip-port" {
            tailf:info
              "Src XOR Dst IP Addr and TCP/UDP Port";
          }
          enum "src-dst-port" {
            tailf:info
              "Src XOR Dst TCP/UDP Port";
          }
          enum "src-ip" {
            tailf:info
              "Src IP Addr";
          }
          enum "src-mac" {
            tailf:info
              "Src Mac Addr";
          }
          enum "src-mixed-ip-port" {
            tailf:info
              "Src IP Addr and TCP/UDP Port";
          }
          enum "src-port" {
            tailf:info
              "Src TCP/UDP Port";
          }
        }
      }
    }
    container l2 {
      tailf:ncs-device-type "cli-ned";
      tailf:display-when "not(../../ncs:module) or ../../ncs:module[ncs:name='tailf-ned-cisco-ios']";
      tailf:info
        "Layer 2 configuration";
      list vfi {
        tailf:info
          "Configure a virtual forwarding instance";
        tailf:cli-suppress-mode;
        tailf:cli-delete-when-empty;
        tailf:cli-compact-syntax;
        key "name";
        leaf name {
          type string {
            tailf:info
              "WORD;;VFI name";
          }
        }
        leaf point-to-point {
          tailf:info
            "Point-to-point configuration mode";
          tailf:cli-full-command;
          type empty;
        }
      }
    }
    container l2protocol-tunnel {
      tailf:ncs-device-type "cli-ned";
      tailf:display-when "not(../../ncs:module) or ../../ncs:module[ncs:name='tailf-ned-cisco-ios']";
      tailf:info
        "Tunnel Layer2 protocols";
      leaf cos {
        tailf:info
          "Class of Service";
        type uint8 {
          tailf:info
            "<0-7>;;priority value";
          range "0..7";
        }
      }
      container global {
        tailf:info
          "Global settings";
        leaf drop-threshold {
          tailf:info
            "L2PT packets drop threshold";
          type uint16 {
            tailf:info
              "<100-20000>;;Packets per second";
            range "100..20000";
          }
        }
      }
    }
    container system {
      tailf:ncs-device-type "cli-ned";
      tailf:display-when "not(../../ncs:module) or ../../ncs:module[ncs:name='tailf-ned-cisco-ios']";
      tailf:info
        "Set the system configuration";
      container env {
        tailf:info
          "Set the system environment settings";
        container temperature {
          tailf:info
            "Set the system temperature settings";
          container threshold {
            tailf:info
              "Set the system temperature thresholds";
            leaf yellow {
              tailf:info
                "Set the yellow threshold";
              type uint8 {
                tailf:info
                  "<0-25>;;Delta value from Red threshold in Degree Celsius";
                range "0..25";
              }
            }
          }
        }
      }
      container mtu {
        tailf:info
          "Set the system Maximum Transmission Unit (MTU)";
        leaf size {
          tailf:cli-drop-node-name;
          type uint16 {
            tailf:info
              "<1500-1998>;;MTU size in bytes";
            range "1500..1998";
          }
        }
        leaf jumbo {
          tailf:info
            "Set Jumbo MTU value for GigabitEthernet or TenGigabitEthernet interfaces";
          type uint16 {
            tailf:info
              "<1500-9000>;;Jumbo MTU size in bytes";
            range "1500..9000";
          }
        }
        leaf routing {
          tailf:info
            "Set the Routing MTU for the system";
          type uint16 {
            tailf:info
              "<1500-1500>;;MTU size in bytes";
            range "1500";
          }
        }
      }
    }
    container errdisable {
      tailf:ncs-device-type "cli-ned";
      tailf:display-when "not(../../ncs:module) or ../../ncs:module[ncs:name='tailf-ned-cisco-ios']";
      tailf:info
        "Error disable";
      container detect {
        tailf:info
          "Error disable detection";
        container cause {
          tailf:info
            "Enable error disable detection for application";
          leaf all {
            tailf:info
              "Enable error detection on all cases";
            tailf:cli-full-command;
            type empty;
          }
          leaf arp-inspection {
            tailf:info
              "Enable error detection for arp inspection";
            tailf:cli-full-command;
            type empty;
          }
          leaf bpduguard {
            tailf:info
              "Enable error detection on bpdu-guard";
            tailf:cli-full-command;
            type empty;
          }
          leaf dhcp-rate-limit {
            tailf:info
              "Enable error detection on dhcp-rate-limit";
            tailf:cli-full-command;
            type empty;
          }
          leaf dtp-flap {
            tailf:info
              "Enable error detection on dtp-flapping";
            tailf:cli-full-command;
            type empty;
          }
          leaf gbic-invalid {
            tailf:info
              "Enable error detection on gbic-invalid";
            tailf:cli-full-command;
            type empty;
          }
          leaf inline-power {
            tailf:info
              "Enable error detection for inline-power";
            tailf:cli-full-command;
            type empty;
          }
          leaf l2ptguard {
            tailf:info
              "Enable timer to recover from l2protocol-tunnel error disable state";
            tailf:cli-full-command;
            type empty;
          }
          leaf link-flap {
            tailf:info
              "Enable error detection on linkstate-flapping";
            tailf:cli-full-command;
            type empty;
          }
          leaf loopback {
            tailf:info
              "Enable error detection on loopback";
            tailf:cli-full-command;
            type empty;
          }
          leaf mlacp-minlink {
            tailf:cli-full-command;
            type empty;
          }
          leaf pagp-flap {
            tailf:info
              "Enable error detection on pagp-flapping";
            tailf:cli-full-command;
            type empty;
          }
          leaf pppoe-ia-rate-limit {
            tailf:info
              "Enable error detection on PPPoE IA rate-limit";
            tailf:cli-full-command;
            type empty;
          }
          leaf security-violation {
            tailf:info
              "Enable error detection on 802.1x-guard";
            tailf:cli-full-command;
            type empty;
          }
          leaf sfp-config-mismatch {
            tailf:info
              "Enable error detection on SFP config mismatch";
            tailf:cli-full-command;
            type empty;
          }
          leaf small-frame {
            tailf:info
              "Enable error detection on small_frame";
            tailf:cli-full-command;
            type empty;
          }
        }
      }
      container flap-setting {
        tailf:info
          "Error disable flap detection setting";
        container cause {
          tailf:info
            "Set error disable flap parameters for application";
          container dtp-flap {
            tailf:info
              "Set the variables related to detection of dtp flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
          container link-flap {
            tailf:info
              "Set the variables related to detection of link flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
          container pagp-flap {
            tailf:info
              "Set the variables related to detection of pagp flaps";
            tailf:cli-compact-syntax;
            tailf:cli-sequence-commands;
            leaf max-flaps {
              tailf:info
                "maximum flaps allowed before setting to errdisable";
              type uint8 {
                tailf:info
                  "<1-100>;;flap count";
                range "1..100";
              }
            }
            leaf time {
              tailf:info
                "time period the flaps are counted";
              type uint8 {
                tailf:info
                  "<1-120>;;flap count time";
                range "1..120";
              }
            }
          }
        }
      }
      container recovery {
        tailf:info
          "Error disable recovery";
        container cause {
          tailf:info
            "Enable error disable recovery for application";
          leaf all {
            tailf:info
              "Enable timer to recover from all error causes";
            type empty;
          }
          leaf arp-inspection {
            tailf:info
              "Enable timer to recover from arp inspection error disable state";
            type empty;
          }
          leaf bpduguard {
            tailf:info
              "Enable timer to recover from BPDU Guard error";
            type empty;
          }
          leaf channel-misconfig {
            tailf:info
              "(STP)  Enable timer to recover from channel misconfig error";
            type empty;
          }
          leaf dhcp-rate-limit {
            tailf:info
              "Enable timer to recover from dhcp-rate-limit error";
            type empty;
          }
          leaf dtp-flap {
            tailf:info
              "Enable timer to recover from dtp-flap error";
            type empty;
          }
          leaf gbic-invalid {
            tailf:info
              "Enable timer to recover from invalid GBIC error";
            type empty;
          }
          leaf inline-power {
            tailf:info
              "Enable timer to recover from inline-power error";
            type empty;
          }
          leaf l2ptguard {
            tailf:info
              "Enable timer to recover from l2protocol-tunnel error disable state";
            type empty;
          }
          leaf link-flap {
            tailf:info
              "Enable timer to recover from link-flap error";
            type empty;
          }
          leaf link-monitor-failure {
            type empty;
          }
          leaf loopback {
            tailf:info
              "Enable timer to recover from loopback error";
            type empty;
          }
          leaf mac-limit {
            tailf:info
              "Enable timer to recover from mac limit disable state";
            type empty;
          }
          leaf mlacp-minlink {
            tailf:cli-full-command;
            type empty;
          }
          container oam-remote-failure {
            tailf:cli-display-separated;
            presence "true";
            leaf critical-event {
              tailf:cli-full-command;
              type empty;
            }
            leaf dying-gasp {
              tailf:cli-full-command;
              type empty;
            }
            leaf link-fault {
              tailf:cli-full-command;
              type empty;
            }
          }
          leaf pagp-flap {
            tailf:info
              "Enable timer to recover from pagp-flap error";
            type empty;
          }
          leaf port-mode-failure {
            tailf:info
              "Enable timer to recover from port mode change failure";
            type empty;
          }
          leaf pppoe-ia-rate-limit {
            tailf:info
              "Enable timer to recover from PPPoE IA rate-limit error";
            type empty;
          }
          leaf psp {
            type empty;
          }
          leaf psecure-violation {
            tailf:info
              "Enable timer to recover from psecure violation error";
            type empty;
          }
          leaf security-violation {
            tailf:info
              "Enable timer to recover from 802.1x violation error";
            type empty;
          }
          leaf sfp-config-mismatch {
            tailf:info
              "Enable timer to recover from SFP config mismatch error";
            type empty;
          }
          leaf small-frame {
            tailf:info
              "Enable timer to recover from small frame error";
            type empty;
          }
          leaf storm-control {
            tailf:info
              "Enable timer to recover from storm-control error";
            type empty;
          }
          leaf udld {
            tailf:info
              "Enable timer to recover from udld error";
            type empty;
          }
          leaf unicast-flood {
            type empty;
          }
          leaf vmps {
            tailf:info
              "Enable timer to recover from vmps shutdown error";
            type empty;
          }
        }
        leaf interval {
          tailf:info
            "Error disable recovery timer value";
          type uint32 {
            tailf:info
              "<30-86400>;;timer-interval(sec)";
            range "30..86400";
          }
        }
      }
    }
    container monitor {
      tailf:ncs-device-type "cli-ned";
      tailf:display-when "not(../../ncs:module) or ../../ncs:module[ncs:name='tailf-ned-cisco-ios']";
      tailf:info
        "Monitoring different system events";
      container event-trace {
        tailf:info
          "Tracing of system events";
      }
      list session {
        tailf:info
          "Configure a SPAN session";
        tailf:cli-suppress-mode;
        tailf:cli-delete-when-empty;
        tailf:cli-compact-syntax;
        tailf:cli-incomplete-command;
        key "id";
        leaf id {
          type uint8 {
            tailf:info
              "<1-66>;;SPAN session number";
            range "1..66";
          }
        }
        container destination {
          tailf:info
            "SPAN destination interface or VLAN";
          leaf interface {
            tailf:info
              "SPAN destination interface";
            type string;
          }
          leaf encapsulation {
            tailf:cli-hide-in-submode;
            tailf:info
              "Set encapsulation for destination interface";
            type enumeration {
              enum "dot1q" {
                tailf:info
                  "interface uses only dot1q encapsulation";
              }
              enum "isl" {
                tailf:info
                  "interface uses only isl encapsulation";
              }
              enum "replicate" {
                tailf:info
                  "interface replicates source encapsulation";
              }
            }
          }
          leaf ingress {
            tailf:info
              "Enable ingress traffic forwarding";
            tailf:cli-hide-in-submode;
            type empty;
          }
          leaf ingress-encap {
            tailf:cli-drop-node-name;
            tailf:cli-hide-in-submode;
            when '../ingress' {
              tailf:xpath-root 3;
              tailf:dependency "../ingress";
            }
            type enumeration {
              enum "dot1q" {
                tailf:info
                  "ingress forwarding using dot1q encapsulation";
              }
              enum "isl" {
                tailf:info
                  "ingress forwarding using isl encapsulation";
              }
              enum "untagged" {
                tailf:info
                  "ingress forwarding using untagged encapsulation";
              }
            }
          }
          leaf vlan {
            tailf:info
              "Set default VLAN for untagged ingress traffic";
            tailf:cli-hide-in-submode;
            when '../ingress' {
              tailf:xpath-root 3;
              tailf:dependency "../ingress";
            }
            type uint16 {
              tailf:info
                "<1-4094>;;Default VLAN for untagged ingress traffic";
              range "1..4094";
            }
          }
        }
        container source {
          tailf:info
            "SPAN source interface, VLAN ";
          container interface {
            tailf:info
              "SPAN source interface";
            tailf:cli-diff-dependency "/ios:interface" {
              tailf:xpath-root 3;
            }
            uses interface-grouping;
          }
          container vlan {
            tailf:info
              "SPAN source VLAN";
            tailf:cli-compact-syntax;
            tailf:cli-flatten-container;
            tailf:cli-sequence-commands;
            leaf vlan {
              tailf:cli-drop-node-name;
              type uint16 {
                tailf:info
                  "<1-4094>;;SPAN source VLAN";
                range "1..4094";
              }
            }
            leaf direction {
              tailf:cli-drop-node-name;
              type enumeration {
                enum "both" {
                  tailf:info
                    "Monitor received and transmitted traffic";
                }
                enum "rx" {
                  tailf:info
                    "Monitor received traffic only";
                }
                enum "tx" {
                  tailf:info
                    "Monitor transmitted traffic only";
                }
              }
            }
          }
        }
      }
    }
    list tftp-server {
      tailf:ncs-device-type "cli-ned";
      tailf:display-when "not(../ncs:module) or ../ncs:module[ncs:name='tailf-ned-cisco-ios']";
      tailf:info
        "Provide TFTP service for netload requests";
      tailf:cli-suppress-mode;
      tailf:cli-delete-when-empty;
      tailf:cli-compact-syntax;
      key "name";
      leaf name {
        type string;
      }
    }
    container radius-server {
      tailf:ncs-device-type "cli-ned";
      tailf:display-when "not(../../ncs:module) or ../../ncs:module[ncs:name='tailf-ned-cisco-ios']";
      tailf:info
        "Modify RADIUS query parameters";
      list host {
        tailf:info
          "Specify a RADIUS server";
        tailf:cli-suppress-mode;
        tailf:cli-delete-when-empty;
        tailf:cli-compact-syntax;
        key "id";
        leaf id {
          type string {
            tailf:info
              "Hostname or A.B.C.D;;IP address of RADIUS server";
          }
        }
        leaf acct-port {
          tailf:info
            "UDP port for RADIUS accounting server (default is 1646)";
          type uint16 {
            tailf:info
              "<0-65535>;;Port number";
            range "0..65535";
          }
        }
        leaf auth-port {
          tailf:info
            "UDP port for RADIUS authentication server (default is 1645)";
          type uint16 {
            tailf:info
              "<0-65535>;;Port number";
            range "0..65535";
          }
        }
        leaf key {
          tailf:info
            "per-server encryption key (overrides default)";
          type string {
            tailf:info
              "LINE;;The UNENCRYPTED (cleartext) server key";
          }
        }
      }
    }
    container radius {
      tailf:ncs-device-type "cli-ned";
      tailf:display-when "not(../../ncs:module) or ../../ncs:module[ncs:name='tailf-ned-cisco-ios']";
      tailf:info
        "RADIUS server configuration command";
      list filter {
        tailf:info
          "Packet filter configuration";
        key "id";
        leaf id {
          type string {
            tailf:info
              "WORD;;Name of the filter (max 31 characters, longer will be rejected";
          }
        }
        leaf match {
          tailf:cli-drop-node-name;
          tailf:cli-prefix-key;
          type enumeration {
            enum "match-all" {
              tailf:info
                "Filter if all of the attributes matches";
            }
            enum "match-any" {
              tailf:info
                "Filter if any of the attributes matches";
            }
          }
        }
      }
      list server {
        tailf:info
          "Server configuration";
        key "id";
        leaf id {
          type string {
            tailf:info
              "WORD;;Name for the radius server configuration";
          }
        }
        container address {
          tailf:info
            "Specify the radius server address";
          container ipv4 {
            tailf:info
              "IPv4 Address";
            tailf:cli-compact-syntax;
            tailf:cli-sequence-commands {
              tailf:cli-reset-siblings;
            }
            leaf host {
              tailf:cli-drop-node-name;
              type string {
                tailf:info
                  "Hostname or A.B.C.D;;IPv4 Address of radius server";
              }
            }
            leaf auth-port {
              tailf:info
                "UDP port for RADIUS authentication server (default is 1645)";
              tailf:cli-optional-in-sequence;
              type uint16 {
                tailf:info
                  "<0-65535>;;Port number";
                range "0..65535";
              }
            }
            leaf acct-port {
              tailf:info
                "UDP port for RADIUS accounting server (default is 1646)";
              type uint16 {
                tailf:info
                  "<0-65535>;;Port number";
                range "0..65535";
              }
            }
          }
        }
        container backoff {
          tailf:info
            "Retry backoff pattern(Default is retransmits with constant delay)";
          container exponential {
            tailf:info
              "Exponential retransmit backoff";
            tailf:cli-compact-syntax;
            tailf:cli-sequence-commands {
              tailf:cli-reset-siblings;
            }
            presence "true";
            leaf max-delay {
              tailf:cli-optional-in-sequence;
              tailf:info
                "Max delay between retransmits(default is 3 min)";
              type uint8 {
                tailf:info
                  "<1-120>;;Max time (in minutes) to delay between retransmits";
                range "1..120";
              }
            }
            leaf backoff-retry {
              tailf:info
                "Exponential backoff retry number(default is 8)";
              type uint8 {
                tailf:info
                  "<1-50>;;Number of retransmits in the exponential backoff mode";
                range "1..50";
              }
            }
          }
        }
        container key {
          tailf:info
            "Per-server encryption key";
          tailf:cli-compact-syntax;
          tailf:cli-sequence-commands {
            tailf:cli-reset-siblings;
          }
          leaf encryption {
            tailf:cli-drop-node-name;
            tailf:cli-incomplete-command;
            tailf:cli-optional-in-sequence;
            type enumeration {
              enum "0" {
                tailf:info
                  "Specifies an UNENCRYPTED key will follow";
              }
              enum "5" {
                tailf:info
                  "Specifies a HIDDEN key will follow";
              }
            }
          }
          leaf key {
            tailf:cli-drop-node-name;
            tailf:cli-multi-value;
            type string {
              tailf:info
                "LINE;;The UNCRYPTED (cleartext) shared key";
            }
          }
        }
      }
    }
    container zone {
      tailf:ncs-device-type "cli-ned";
      tailf:display-when "not(../../ncs:module) or ../../ncs:module[ncs:name='tailf-ned-cisco-ios']";
      tailf:info
        "FW with zoning";
      list security {
        tailf:info
          "Security zone";
        tailf:cli-mode-name "config-sec-zone";
        tailf:cli-full-command;
        key "id";
        leaf id {
          type string {
            tailf:info
              "WORD;;Name of security zone";
          }
        }
        leaf description {
          tailf:info
            "Zone description";
          tailf:cli-multi-value;
          type string {
            tailf:info
              "LINE;;Description of zone (up to 200 characters)";
          }
        }
      }
    }
    container zone-pair {
      tailf:ncs-device-type "cli-ned";
      tailf:display-when "not(../../ncs:module) or ../../ncs:module[ncs:name='tailf-ned-cisco-ios']";
      tailf:info
        "Zone pair command";
      list security {
        tailf:info
          "Zone-pair name";
        tailf:cli-sequence-commands {
          tailf:cli-reset-siblings;
        }
        tailf:cli-mode-name "config-sec-zone-pair";
        key "id";
        leaf id {
          type string {
            tailf:info
              "WORD;;Name of zone-pair";
          }
        }
        leaf source {
          tailf:info
            "Source zone";
          tailf:cli-hide-in-submode;
          tailf:non-strict-leafref {
            path "/ncs:devices/ncs:device/ncs:config/ios:zone/security/id" {
              tailf:xpath-root 3;
            }
          }
          type string {
            tailf:info
              "WORD;;Name of source zone";
          }
        }
        leaf destination {
          tailf:info
            "Destination zone";
          tailf:cli-hide-in-submode;
          tailf:non-strict-leafref {
            path "/ncs:devices/ncs:device/ncs:config/ios:zone/security/id" {
              tailf:xpath-root 3;
            }
          }
          type string {
            tailf:info
              "WORD;;Name of destination zone";
          }
        }
        leaf description {
          tailf:info
            "Zone description";
          tailf:cli-break-sequence-commands;
          tailf:cli-multi-value;
          type string {
            tailf:info
              "LINE;;Description of zone (up to 200 characters)";
            length "1..200";
          }
        }
        container service-policy {
          tailf:info
            "Configure CBAC Service Policy";
          container type {
            tailf:info
              "Service Policy type";
            leaf inspect {
              tailf:info
                "Configure CBAC Service Policy type inspect";
              type string;
              tailf:non-strict-leafref {
                path "/ncs:devices/ncs:device/ncs:config/ios:policy-map/name" {
                  tailf:xpath-root 3;
                }
              }
            }
          }
        }
      }
    }
    container aaa {
      tailf:ncs-device-type "cli-ned";
      tailf:display-when "not(../../ncs:module) or ../../ncs:module[ncs:name='tailf-ned-cisco-ios']";
      tailf:info
        "Authentication, Authorization and Accounting.";
      tailf:cli-incomplete-command;
      leaf new-model {
        tailf:info
          "Enable NEW access control commands and functions.(Disables OLD commands.)";
        type empty;
      }
      container group {
        tailf:info
          "AAA group definitions";
        tailf:cli-diff-dependency "/ios:aaa/new-model" {
          tailf:xpath-root 3;
        }
        container server {
          tailf:info
            "AAA Server group definitions";
          list tacacsplus {
            tailf:alt-name "tacacs+";
            tailf:info
              "Tacacs+ server-group definition";
            tailf:cli-full-command;
            key "name";
            leaf name {
              type string {
                tailf:info
                  "WORD;;Server-group name";
              }
            }
            list server-private {
              tailf:info
                "Define a private TACACS server (per group)";
              tailf:cli-suppress-mode;
              tailf:cli-delete-when-empty;
              tailf:cli-compact-syntax;
              tailf:cli-sequence-commands;
              tailf:cli-reset-container;
              key "name";
              leaf name {
                type host-type {
                  tailf:info
                    "Hostname or A.B.C.D;;IP address of TACACS server";
                }
              }
              leaf timeout {
                tailf:info
                  "Time to wait for this TACACS server to reply (overrides default)";
                tailf:cli-optional-in-sequence;
                type uint16 {
                  tailf:info
                    "<1-1000>;;Timeout value in seconds to wait for server to reply";
                  range "1..1000";
                }
              }
              container key {
                tailf:info
                  "per-server encryption key (overrides default)";
                tailf:cli-compact-syntax;
                tailf:cli-flatten-container;
                tailf:cli-sequence-commands;
                leaf encryption {
                  tailf:cli-drop-node-name;
                  tailf:cli-incomplete-command;
                  tailf:cli-optional-in-sequence;
                  type enumeration {
                    enum "0" {
                      tailf:info
                        "Specifies an UNENCRYPTED key will follow";
                    }
                    enum "7" {
                      tailf:info
                        "Specifies HIDDEN key will follow";
                    }
                  }
                }
                leaf key {
                  tailf:cli-drop-node-name;
                  tailf:cli-full-command;
                  tailf:cli-multi-value;
                  type string {
                    tailf:info
                      "LINE;;The UNENCRYPTED (cleartext) shared key";
                  }
                }
              }
            }
            container ip {
              tailf:info
                "Internet Protocol config commands";
              container tacacs {
                tailf:info
                  "TACACS configuration commands";
                container source-interface {
                  tailf:info
                    "Specify interface for source address in TACACS packets";
                  tailf:cli-diff-dependency "/ios:interface" {
                    tailf:xpath-root 3;
                  }
                  uses interface-grouping;
                }
              }
            }
          }
          list radius {
            tailf:info
              "Radius server-group definition";
            tailf:cli-mode-name "config-sg-radius";
            key "name";
            leaf name {
              type string {
                tailf:info
                  "WORD;;Server-group name";
              }
            }
            container server {
              tailf:info
                "Specify a RADIUS server";
              list name {
                tailf:info
                  "Name of radius server";
                tailf:cli-suppress-mode;
                key "name";
                leaf name {
                  type string;
                  tailf:non-strict-leafref {
                    path "/ncs:devices/ncs:device/ncs:config/ios:aaa/group/server/radius/name" {
                      tailf:xpath-root 3;
                    }
                  }
                }
              }
              list direct {
                tailf:cli-drop-node-name;
                tailf:cli-compact-syntax;
                tailf:cli-suppress-mode;
                key "name";
                leaf name {
                  type inet:host {
                    tailf:info
                      "Hostname or A.B.C.D;;IP address of RADIUS server";
                  }
                  tailf:cli-disallow-value "name";
                }
                leaf auth-port {
                  tailf:info
                    "UDP port for RADIUS authentication server (default is 1645)";
                  type uint16 {
                    tailf:info
                      "<0-65535>;;Port number";
                    range "0..65535";
                  }
                }
                leaf acct-port {
                  tailf:info
                    "UDP port for RADIUS accounting server (default is 1646)";
                  type uint16 {
                    tailf:info
                      "<0-65535>;;Port number";
                    range "0..65535";
                  }
                }
              }
            }
            container ip {
              tailf:info
                "Internet Protocol config commands";
              container radius {
                tailf:info
                  "RADIUS configuration commands";
                leaf source-interface {
                  tailf:info
                    "Specify interface for source address in RADIUS packets";
                  type string;
                }
              }
              container vrf {
                tailf:info
                  "Set VPN Routing Forwarding to use with the servers";
                leaf forwarding {
                  tailf:info
                    "Configure forwarding table";
                  tailf:cli-diff-dependency "/ios:ip/vrf" {
                    tailf:xpath-root 3;
                  }
                  tailf:cli-diff-dependency "/ios:vrf/definition" {
                    tailf:xpath-root 3;
                  }
                  type string {
                    tailf:info
                      "WORD;;Table name";
                  }
                }
              }
            }
          }
        }
      }
      container authentication {
        tailf:info
          "Authentication configurations parameters.";
        tailf:cli-diff-dependency "/ios:aaa/new-model" {
          tailf:xpath-root 3;
        }
        container dot1x {
          tailf:info
            "Set authentication lists for IEEE 802.1x.";
          list dot1x-list {
            tailf:cli-suppress-mode;
            tailf:cli-delete-when-empty;
            tailf:cli-compact-syntax;
            key "name";
            leaf name {
              type string {
                tailf:info
                  "WORD;;Named authentication list";
              }
            }
            uses aaa-authentication-dot1x-grouping;
          }
          container default {
            tailf:info
              "The default authentication list.";
            uses aaa-authentication-dot1x-grouping;
          }
        }
        container enable {
          tailf:info
            "Set authentication list for enable.";
          container default {
            tailf:info
              "The default authentication list.";
            tailf:cli-compact-syntax;
            leaf enable {
              tailf:info
                "Use enable password for authentication.";
              type empty;
            }
            leaf group {
              tailf:info
                "Use Server-group";
              type union {
                type string {
                  tailf:info
                    "WORD;;Server-group name";
                }
                type enumeration {
                  enum "radius" {
                    tailf:info
                      "Use list of all Radius hosts.";
                  }
                  enum "tacacs+" {
                    tailf:info
                      "+  Use list of all Tacacs+ hosts.";
                  }
                }
              }
            }
            leaf line {
              tailf:info
                "Use line password for authentication.";
              type empty;
            }
            leaf none {
              tailf:info
                "No authentication.";
              tailf:cli-full-command;
              type empty;
            }
          }
        }
        list login {
          tailf:info
            "Set authentication lists for logins.";
          tailf:cli-suppress-mode;
          tailf:cli-delete-when-empty;
          tailf:cli-compact-syntax;
          key "name";
          leaf name {
            type string {
              tailf:info
                "WORD;;Named authentication list (max 31 characters,longer will be rejected).";
              length "1..31";
            }
          }
          leaf group {
            tailf:info
              "Use Server-group";
            type union {
              type string {
                tailf:info
                  "WORD;;Server-group name";
              }
              type enumeration {
                enum "ldap" {
                  tailf:info
                    "Use list of all LDAP hosts.";
                }
                enum "radius" {
                  tailf:info
                    "Use list of all Radius hosts.";
                }
                enum "tacacs" {
                  tailf:info
                    "+  Use list of all Tacacs+ hosts.";
                }
              }
            }
          }
          leaf local {
            tailf:info
              "Use local username authentication.";
            type empty;
          }
          leaf none {
            tailf:info
              "NO authentication.";
            tailf:cli-full-command;
            type empty;
          }
        }
        list ppp {
          tailf:info
            "Set authentication lists for ppp.";
          tailf:cli-suppress-mode;
          tailf:cli-delete-when-empty;
          tailf:cli-compact-syntax;
          tailf:cli-sequence-commands {
            tailf:cli-reset-all-siblings;
          }
          key "id";
          leaf id {
            type string {
              tailf:info
                "WORD;;Named authentication list (max 31 characters, longer will be rejected).";
              length "1..31";
            }
          }
          container a1 {
            tailf:cli-drop-node-name;
            tailf:cli-flatten-container;
            tailf:cli-compact-syntax;
            choice auth-choice {
              leaf if-needed {
                tailf:info
                  "Only authenticate if needed.";
                tailf:cli-optional-in-sequence;
                type empty;
              }
              leaf none {
                tailf:info
                  "NO authentication.";
                type empty;
              }
              leaf krb5 {
                tailf:info
                  "Use Kerberos 5 authentication.";
                type empty;
              }
              leaf local {
                tailf:info
                  "Use local username authentication.";
                type empty;
              }
              leaf local-case {
                tailf:info
                  "Use case-sensitive local username authentication.";
                type empty;
              }
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
            }
          }
          container a2 {
            when 'not(../a1/none)' {
              tailf:xpath-root 3;
              tailf:dependency "../a1/none";
            }
            tailf:cli-drop-node-name;
            tailf:cli-flatten-container;
            tailf:cli-compact-syntax;
            choice auth-choice {
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf none {
                tailf:info
                  "NO authentication.";
                type empty;
              }
              leaf krb5 {
                when 'not(../../a1/krb5)' {
                  tailf:xpath-root 3;
                  tailf:dependency "../../a1/krb5";
                }
                tailf:info
                  "Use Kerberos 5 authentication.";
                type empty;
              }
              leaf local {
                when 'not(../../a1/local) and not(../../a1/local-case)' {
                  tailf:xpath-root 3;
                  tailf:dependency "../../a1/local";
                  tailf:dependency "../../a1/local-case";
                }
                tailf:info
                  "Use local username authentication.";
                type empty;
              }
              leaf local-case {
                when 'not(../../a1/local) and not(../../a1/local-case)' {
                  tailf:xpath-root 3;
                  tailf:dependency "../../a1/local";
                  tailf:dependency "../../a1/local-case";
                }
                tailf:info
                  "Use case-sensitive local username authentication.";
                type empty;
              }
            }
          }
          container a3 {
            when 'not(../a2/none) and not (../a1/none)' {
              tailf:xpath-root 3;
              tailf:dependency "../a1/none";
              tailf:dependency "../a2/none";
            }
            tailf:cli-drop-node-name;
            tailf:cli-flatten-container;
            tailf:cli-compact-syntax;
            choice auth-choice {
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf none {
                tailf:info
                  "NO authentication.";
                type empty;
              }
              leaf krb5 {
                when 'not(../../a1/krb5) and not(../../a2/krb5)' {
                  tailf:xpath-root 3;
                  tailf:dependency "../../a1/krb5";
                  tailf:dependency "../../a2/krb5";
                }
                tailf:info
                  "Use Kerberos 5 authentication.";
                type empty;
              }
              leaf local {
                when 'not(../../a1/local) and not(../../a1/local-case) and not(../../a2/local) and not(../../a2/local-case)' {
                  tailf:xpath-root 3;
                  tailf:dependency "../../a1/local";
                  tailf:dependency "../../a1/local-case";
                  tailf:dependency "../../a2/local";
                  tailf:dependency "../../a2/local-case";
                }
                tailf:info
                  "Use local username authentication.";
                type empty;
              }
              leaf local-case {
                when 'not(../../a1/local) and not(../../a1/local-case) and not(../../a2/local) and not(../../a2/local-case)' {
                  tailf:xpath-root 3;
                  tailf:dependency "../../a1/local";
                  tailf:dependency "../../a1/local-case";
                  tailf:dependency "../../a2/local";
                  tailf:dependency "../../a2/local-case";
                }
                tailf:info
                  "Use case-sensitive local username authentication.";
                type empty;
              }
            }
          }
          container a4 {
            when 'not(../a2/none) and not(../a1/none) and not(../a3/none)' {
              tailf:xpath-root 3;
              tailf:dependency "../a1/none";
              tailf:dependency "../a2/none";
              tailf:dependency "../a3/none";
            }
            tailf:cli-drop-node-name;
            tailf:cli-flatten-container;
            tailf:cli-compact-syntax;
            choice auth-choice {
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf none {
                tailf:info
                  "NO authentication.";
                type empty;
              }
              leaf krb5 {
                when 'not(../../a1/krb5) and not(../../a2/krb5) and not(../../a3/krb5)' {
                  tailf:xpath-root 3;
                  tailf:dependency "../../a1/krb5";
                  tailf:dependency "../../a2/krb5";
                  tailf:dependency "../../a3/krb5";
                }
                tailf:info
                  "Use Kerberos 5 authentication.";
                type empty;
              }
              leaf local {
                when 'not(../../a1/local) and not(../../a1/local-case) and not(../../a2/local) and not(../../a2/local-case) and not(../../a3/local) and not(../../a3/local-case)' {
                  tailf:xpath-root 3;
                  tailf:dependency "../../a1/local";
                  tailf:dependency "../../a1/local-case";
                  tailf:dependency "../../a2/local";
                  tailf:dependency "../../a2/local-case";
                  tailf:dependency "../../a3/local";
                  tailf:dependency "../../a3/local-case";
                }
                tailf:info
                  "Use local username authentication.";
                type empty;
              }
              leaf local-case {
                when 'not(../../a1/local) and not(../../a1/local-case) and not(../../a2/local) and not(../../a2/local-case) and not(../../a3/local) and not(../../a3/local-case)' {
                  tailf:xpath-root 3;
                  tailf:dependency "../../a1/local";
                  tailf:dependency "../../a1/local-case";
                  tailf:dependency "../../a2/local";
                  tailf:dependency "../../a2/local-case";
                  tailf:dependency "../../a3/local";
                  tailf:dependency "../../a3/local-case";
                }
                tailf:info
                  "Use case-sensitive local username authentication.";
                type empty;
              }
            }
          }
        }
      }
      container authorization {
        tailf:info
          "Authorization configurations parameters.";
        tailf:cli-incomplete-command;
        tailf:cli-diff-dependency "/ios:aaa/new-model" {
          tailf:xpath-root 3;
        }
        list commands {
          tailf:info
            "For exec (shell) commands.";
          tailf:cli-suppress-mode;
          tailf:cli-delete-when-empty;
          tailf:cli-compact-syntax;
          tailf:cli-incomplete-command;
          key "level list-name";
          leaf level {
            tailf:info
              "Enable level";
            type uint8 {
              range "0..15";
            }
          }
          leaf list-name {
            tailf:cli-incomplete-command;
            tailf:cli-disallow-value "group";
            type union {
              type enumeration {
                enum "default" {
                  tailf:info
                    "The default authorization list.";
                }
              }
              type string {
                tailf:info
                  "WORD;;Named authorization list.";
              }
            }
          }
          leaf group {
            tailf:info
              "Use server-group.";
            tailf:cli-disallow-value "if-authenticated|local|none";
            type union {
              type enumeration {
                enum "tacacs+" {
                  tailf:info
                    "Use list of all Tacacs+ hosts.";
                }
              }
              type string {
                tailf:info
                  "WORD;;Server-group name";
              }
            }
          }
          leaf if-authenticated {
            tailf:info
              "Succeed if user has authenticated.";
            type empty;
          }
          leaf local {
            tailf:info
              "Use local database.";
            type empty;
          }
          leaf none {
            tailf:info
              "No authorization (always succeeds).";
            type empty;
          }
        }
        leaf console {
          type empty;
        }
        leaf config-commands {
          tailf:info
            "For configuration mode commands.";
          type empty;
        }
        list exec {
          tailf:info
            "For starting an exec (shell).";
          tailf:cli-suppress-mode;
          tailf:cli-delete-when-empty;
          tailf:cli-compact-syntax;
          key "name";
          leaf name {
            type string {
              tailf:info
                "WORD;;Named authorization list (max 31 characters, longer will be rejected).";
            }
          }
          leaf group {
            tailf:info
              "Use server-group.";
            type union {
              type string {
                tailf:info
                  "WORD;;Server-group name";
              }
              type enumeration {
                enum "ldap" {
                  tailf:info
                    "Use list of all LDAP hosts.";
                }
                enum "radius" {
                  tailf:info
                    "Use list of all Radius hosts.";
                }
                enum "tacacs" {
                  tailf:info
                    "+  Use list of all Tacacs+ hosts.";
                }
              }
            }
          }
          leaf local {
            tailf:info
              "Use local database.";
            type empty;
          }
          leaf none {
            tailf:info
              "No authorization (always succeeds).";
            type empty;
          }
        }
        list eventmanager {
          tailf:info
            "For starting an exec (shell).";
          tailf:cli-suppress-mode;
          tailf:cli-delete-when-empty;
          tailf:cli-compact-syntax;
          key "name";
          leaf name {
            type string {
              tailf:info
                "WORD;;Named authorization list (max 31 characters, longer will be rejected).";
            }
          }
          leaf group {
            tailf:info
              "Use server-group.";
            type union {
              type string {
                tailf:info
                  "WORD;;Server-group name";
              }
              type enumeration {
                enum "ldap" {
                  tailf:info
                    "Use list of all LDAP hosts.";
                }
                enum "radius" {
                  tailf:info
                    "Use list of all Radius hosts.";
                }
                enum "tacacs" {
                  tailf:info
                    "+  Use list of all Tacacs+ hosts.";
                }
              }
            }
          }
          leaf local {
            tailf:info
              "Use local database.";
            type empty;
          }
          leaf none {
            tailf:info
              "No authorization (always succeeds).";
            type empty;
          }
        }
        list network {
          tailf:info
            "For network services. (PPP, SLIP, ARAP)";
          tailf:cli-suppress-mode;
          key "id";
          leaf id {
            type union {
              type enumeration {
                enum "default" {
                  tailf:info
                    "The default authorization list.";
                }
              }
              type string {
                tailf:info
                  "WORD;;Named authorization list.";
                length "1..31";
              }
            }
          }
          container a1 {
            tailf:cli-drop-node-name;
            tailf:cli-flatten-container;
            tailf:cli-compact-syntax;
            choice auth-choice {
              leaf if-authenticated {
                tailf:info
                  "Succeed if user has authenticated.";
                type empty;
              }
              leaf none {
                tailf:info
                  "NO authentication.";
                type empty;
              }
              leaf local {
                tailf:info
                  "Use local username authentication.";
                type empty;
              }
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
            }
          }
          container a2 {
            when 'not(../a1/none) and not(../a1/if-authenticated)' {
              tailf:xpath-root 3;
              tailf:dependency "../a1/none";
              tailf:dependency "../a1/if-authenticated";
            }
            tailf:cli-drop-node-name;
            tailf:cli-flatten-container;
            tailf:cli-compact-syntax;
            choice auth-choice {
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf if-authenticated {
                tailf:info
                  "Succeed if user has authenticated.";
                type empty;
              }
              leaf none {
                tailf:info
                  "NO authentication.";
                type empty;
              }
              leaf local {
                when 'not(../../a1/local)' {
                  tailf:xpath-root 3;
                  tailf:dependency "../../a1/local";
                }
                tailf:info
                  "Use local username authentication.";
                type empty;
              }
            }
          }
          container a3 {
            when 'not(../a2/none) and not (../a1/none) and not(../a2/if-authenticated) and not(../a1/if-authenticated)' {
              tailf:xpath-root 3;
              tailf:dependency "../a1/none";
              tailf:dependency "../a2/none";
              tailf:dependency "../a1/if-authenticated";
              tailf:dependency "../a2/if-authenticated";
            }
            tailf:cli-drop-node-name;
            tailf:cli-flatten-container;
            tailf:cli-compact-syntax;
            choice auth-choice {
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf none {
                tailf:info
                  "NO authentication.";
                type empty;
              }
              leaf if-authenticated {
                tailf:info
                  "Succeed if user has authenticated.";
                type empty;
              }
              leaf local {
                when 'not(../../a1/local) and not(../../a2/local)' {
                  tailf:xpath-root 3;
                  tailf:dependency "../../a1/local";
                  tailf:dependency "../../a2/local";
                }
                tailf:info
                  "Use local username authentication.";
                type empty;
              }
            }
          }
          container a4 {
            when 'not(../a2/none) and not(../a1/none) and not(../a3/none) and not(../a2/if-authenticated) and not(../a1/if-authenticated) and not(../a3/if-authenticated)' {
              tailf:xpath-root 3;
              tailf:dependency "../a1/none";
              tailf:dependency "../a2/none";
              tailf:dependency "../a3/none";
              tailf:dependency "../a1/if-authenticated";
              tailf:dependency "../a2/if-authenticated";
              tailf:dependency "../a3/if-authenticated";
            }
            tailf:cli-drop-node-name;
            tailf:cli-flatten-container;
            tailf:cli-compact-syntax;
            choice auth-choice {
              leaf group {
                tailf:info
                  "Use Server-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf cache {
                tailf:info
                  "Use Cached-group";
                type union {
                  type string {
                    tailf:info
                      "WORD;;Server-group name";
                  }
                  type enumeration {
                    enum "radius" {
                      tailf:info
                        "Use list of all Radius hosts.";
                    }
                    enum "tacacs+" {
                      tailf:info
                        "Use list of all Tacacs+ hosts.";
                    }
                  }
                }
              }
              leaf none {
                tailf:info
                  "NO authentication.";
                type empty;
              }
              leaf if-authenticated {
                tailf:info
                  "Succeed if user has authenticated.";
                type empty;
              }
              leaf local {
                when 'not(../../a1/local) and not(../../a2/local) and not(../../a3/local)' {
                  tailf:xpath-root 3;
                  tailf:dependency "../../a1/local";
                  tailf:dependency "../../a2/local";
                  tailf:dependency "../../a3/local";
                }
                tailf:info
                  "Use local username authentication.";
                type empty;
              }
            }
          }
        }
      }
      container accounting {
        tailf:info
          "Accounting configurations parameters.";
        tailf:cli-incomplete-command;
        tailf:cli-diff-dependency "/ios:aaa/new-model" {
          tailf:xpath-root 3;
        }
        list commands {
          tailf:info
            "For exec (shell) commands.";
          tailf:cli-compact-syntax;
          tailf:cli-incomplete-command;
          tailf:cli-sequence-commands;
          tailf:cli-suppress-mode;
          tailf:cli-delete-when-empty;
          key "level list-name";
          leaf level {
            tailf:info
              "Enable level";
            type uint8 {
              range "0..15";
            }
          }
          leaf list-name {
            type union {
              type enumeration {
                enum "default" {
                  tailf:info
                    "The default accounting list.";
                }
              }
              type string {
                tailf:info
                  "WORD;;Named Accounting list. (max 31 characters)";
                length "1..31";
              }
            }
          }
          leaf action-type {
            tailf:cli-drop-node-name;
            tailf:cli-incomplete-command;
            type enumeration {
              enum "none" {
                tailf:info
                  "No accounting.";
              }
              enum "start-stop" {
                tailf:info
                  "Record start and stop without waiting";
              }
              enum "stop-only" {
                tailf:info
                  "Record stop when service terminates.";
              }
            }
          }
          leaf broadcast {
            tailf:info
              "Use Broadcast for Accounting";
            tailf:cli-optional-in-sequence;
            tailf:cli-incomplete-command;
            type empty;
          }
          leaf group {
            tailf:info
              "Use Server-group";
            tailf:cli-full-command;
            type union {
              type string {
                tailf:info
                  "WORD;;Server-group name";
              }
              type enumeration {
                enum "tacacs+" {
                  tailf:info
                    "Use list of all Tacacs+ hosts.";
                }
              }
            }
          }
        }
        list exec {
          tailf:info
            "For starting an exec (shell).";
          tailf:cli-mode-name "cfg-acct-mlist";
          key "name";
          leaf name {
            type string {
              tailf:info
                "WORD;;Named Accounting list (max 31 characters, longer will be rejected).";
            }
          }
          choice accounting-choice {
            leaf none {
              tailf:info
                "No accounting.";
              type empty;
            }
            container start-stop {
              tailf:info
                "Record start and stop without waiting";
              tailf:cli-compact-syntax;
              tailf:cli-sequence-commands;
              tailf:cli-reset-container;
              leaf broadcast {
                tailf:info
                  "Use Broadcast for Accounting";
                tailf:cli-optional-in-sequence;
                type empty;
              }
              leaf group {
                tailf:info
                  "Use Server-group";
                type union {
                  type string {
                    tailf:info
                      "WORD;;Server-group name";
                  }
                  type enumeration {
                    enum "radius" {
                      tailf:info
                        "Use list of all Radius hosts.";
                    }
                    enum "tacacs" {
                      tailf:info
                        "+  Use list of all Tacacs+ hosts.";
                    }
                  }
                }
              }
            }
            container stop-only {
              tailf:info
                "Record stop when service terminates.";
              tailf:cli-compact-syntax;
              tailf:cli-sequence-commands;
              tailf:cli-reset-container;
              leaf broadcast {
                tailf:info
                  "Use Broadcast for Accounting";
                tailf:cli-optional-in-sequence;
                type empty;
              }
              leaf group {
                tailf:info
                  "Use Server-group";
                type union {
                  type string {
                    tailf:info
                      "WORD;;Server-group name";
                  }
                  type enumeration {
                    enum "radius" {
                      tailf:info
                        "Use list of all Radius hosts.";
                    }
                    enum "tacacs" {
                      tailf:info
                        "+  Use list of all Tacacs+ hosts.";
                    }
                  }
                }
              }
            }
          }
        }
        list network {
          tailf:info
            "For network services. (PPP, SLIP, ARAP)";
          tailf:cli-suppress-mode;
          tailf:cli-compact-syntax;
          tailf:cli-sequence-commands {
            tailf:cli-reset-siblings;
          }
          key "id";
          leaf id {
            type union {
              type enumeration {
                enum "default" {
                  tailf:info
                    "The default accounting list.";
                }
              }
              type string {
                tailf:info
                  "WORD;;Named Accounting list.";
                length "1..31";
              }
            }
          }
          choice network-choice {
            case a {
              leaf none {
                tailf:info
                  "No accounting.";
                type empty;
              }
            }
            case b {
              leaf mode {
                tailf:cli-drop-node-name;
                type enumeration {
                  enum "start-stop" {
                    tailf:info
                      "Record start and stop without waiting";
                  }
                  enum "stop-only" {
                    tailf:info
                      "Record stop when service terminates.";
                  }
                }
              }
              leaf broadcast {
                tailf:info
                  "Use Broadcast for Accounting";
                tailf:cli-optional-in-sequence;
                type empty;
              }
              container a1 {
                tailf:cli-compact-syntax;
                tailf:cli-drop-node-name;
                tailf:cli-flatten-container;
                leaf group {
                  tailf:info
                    "Use server-group.";
                  type union {
                    type string {
                      tailf:info
                        "WORD;;Server-group name";
                    }
                    type enumeration {
                      enum "ldap" {
                        tailf:info
                          "Use list of all LDAP hosts.";
                      }
                      enum "radius" {
                        tailf:info
                          "Use list of all Radius hosts.";
                      }
                      enum "tacacs" {
                        tailf:info
                          "+  Use list of all Tacacs+ hosts.";
                      }
                    }
                  }
                }
              }
              container a2 {
                tailf:cli-compact-syntax;
                tailf:cli-drop-node-name;
                tailf:cli-flatten-container;
                leaf group {
                  tailf:info
                    "Use server-group.";
                  type union {
                    type string {
                      tailf:info
                        "WORD;;Server-group name";
                    }
                    type enumeration {
                      enum "ldap" {
                        tailf:info
                          "Use list of all LDAP hosts.";
                      }
                      enum "radius" {
                        tailf:info
                          "Use list of all Radius hosts.";
                      }
                      enum "tacacs" {
                        tailf:info
                          "+  Use list of all Tacacs+ hosts.";
                      }
                    }
                  }
                }
              }
              container a3 {
                tailf:cli-compact-syntax;
                tailf:cli-drop-node-name;
                tailf:cli-flatten-container;
                leaf group {
                  tailf:info
                    "Use server-group.";
                  type union {
                    type string {
                      tailf:info
                        "WORD;;Server-group name";
                    }
                    type enumeration {
                      enum "ldap" {
                        tailf:info
                          "Use list of all LDAP hosts.";
                      }
                      enum "radius" {
                        tailf:info
                          "Use list of all Radius hosts.";
                      }
                      enum "tacacs" {
                        tailf:info
                          "+  Use list of all Tacacs+ hosts.";
                      }
                    }
                  }
                }
              }
              container a4 {
                tailf:cli-compact-syntax;
                tailf:cli-drop-node-name;
                tailf:cli-flatten-container;
                leaf group {
                  tailf:info
                    "Use server-group.";
                  type union {
                    type string {
                      tailf:info
                        "WORD;;Server-group name";
                    }
                    type enumeration {
                      enum "ldap" {
                        tailf:info
                          "Use list of all LDAP hosts.";
                      }
                      enum "radius" {
                        tailf:info
                          "Use list of all Radius hosts.";
                      }
                      enum "tacacs" {
                        tailf:info
                          "+  Use list of all Tacacs+ hosts.";
                      }
                    }
                  }
                }
              }
            }
          }
        }
      }
      leaf session-id {
        tailf:info
          "AAA Session ID";
        tailf:cli-diff-dependency "/ios:aaa/new-model" {
          tailf:xpath-root 3;
        }
        type enumeration {
          enum "common" {
            tailf:info
              "Common Session ID";
          }
          enum "unique" {
            tailf:info
              "Unique Session ID for different accounting types";
          }
        }
      }
    }
    container ethernet {
      tailf:ncs-device-type "cli-ned";
      tailf:display-when "not(../../ncs:module) or ../../ncs:module[ncs:name='tailf-ned-cisco-ios']";
      tailf:info
        "Ethernet configuration";
      list evc {
        tailf:info
          "define an Ethernet virtual connection (EVC)";
        tailf:cli-compact-syntax;
        tailf:cli-full-command;
        key "name";
        leaf name {
          type string {
            tailf:info
              "WORD;;EVC id";
            length "1..100";
          }
        }
      }
      container cfm {
        tailf:info
          "Connectivity Fault Management";
        leaf ieee {
          tailf:info
            "CFM IEEE enable";
          tailf:cli-full-command;
          type empty;
        }
        leaf global {
          tailf:info
            "CFM global enable";
          tailf:cli-full-command;
          type empty;
        }
        list domain {
          tailf:info
            "Configure a domain";
          tailf:cli-mode-name "config-ecfm";
          tailf:cli-compact-syntax;
          tailf:cli-incomplete-command;
          key "name";
          leaf name {
            type string {
              tailf:info
                "WORD;;maintenance domain name";
            }
          }
          leaf level {
            tailf:info
              "Maintenance Level";
            tailf:cli-hide-in-submode;
            type uint8 {
              tailf:info
                "<0-7>  maintenance level number";
            }
          }
          leaf service {
            tailf:info
              "Maintenance Association within Domain";
            type string;
          }
          leaf evc {
            type string;
            tailf:non-strict-leafref {
              path "/ncs:devices/ncs:device/ncs:config/ios:ethernet/evc/name" {
                tailf:xpath-root 3;
              }
            }
          }
          leaf vlan {
            tailf:info
              "VLAN id";
            type uint16 {
              tailf:info
                "<1-4094>;;between 1 and 4094";
              range "1..4094";
            }
          }
        }
      }
    }
    list alarm-contact {
      tailf:ncs-device-type "cli-ned";
      tailf:display-when "not(../ncs:module) or ../ncs:module[ncs:name='tailf-ned-cisco-ios']";
      tailf:cli-suppress-mode;
      tailf:cli-delete-when-empty;
      key "name";
      leaf name {
        type uint8 {
          tailf:info
            "WORD;;Contact number";
          range "1..4";
        }
      }
      leaf description {
        tailf:cli-multi-value;
        type string {
          length "1..80";
        }
      }
      leaf severity {
        type enumeration {
          enum "critical";
          enum "major";
          enum "minor";
        }
      }
      leaf trigger {
        type enumeration {
          enum "open";
          enum "closed";
        }
      }
    }
    container access-list {
      tailf:ncs-device-type "cli-ned";
      tailf:display-when "not(../../ncs:module) or ../../ncs:module[ncs:name='tailf-ned-cisco-ios']";
      tailf:cli-incomplete-command;
      tailf:cli-compact-syntax;
      tailf:info
        "Add an access list entry";
      list access-list-standard-range {
        tailf:cli-drop-node-name;
        tailf:cli-suppress-mode;
        tailf:cli-delete-when-empty;
        tailf:cli-compact-syntax;
        tailf:cli-incomplete-command;
        key "listnumber";
        leaf listnumber {
          tailf:cli-drop-node-name;
          tailf:cli-incomplete-command;
          tailf:cli-incomplete-no;
          tailf:cli-suppress-range;
          type uint16 {
            range "1..99";
            tailf:info
              "<1..99>;;IP standard access list";
          }
        }
        list std-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-drop-node-name;
            tailf:cli-multi-word-key;
            type string {
              tailf:info
                "deny;;Specify packets to reject
                 permit;;Specify packets to forwards
                 remark;;Access list entry comment";
            }
          }
        }
      }
      list access-list-extended-range {
        tailf:cli-drop-node-name;
        tailf:cli-suppress-mode;
        tailf:cli-delete-when-empty;
        tailf:cli-compact-syntax;
        tailf:cli-incomplete-command;
        key "listnumber";
        leaf listnumber {
          tailf:cli-drop-node-name;
          tailf:cli-incomplete-command;
          tailf:cli-incomplete-no;
          tailf:cli-suppress-range;
          type uint16 {
            range "100..199";
            tailf:info
              "<100..199>;;IP extended access list";
          }
        }
        list ext-access-list-rule {
          tailf:cli-suppress-mode;
          tailf:cli-delete-when-empty;
          tailf:cli-drop-node-name;
          tailf:cli-compact-syntax;
          tailf:cli-show-long-obu-diffs;
          ordered-by user;
          key "rule";
          leaf rule {
            tailf:cli-drop-node-name;
            tailf:cli-multi-word-key;
            type string {
              tailf:info
                "deny;;Specify packets to rejectdynamic;;Specify DYNAMIC list of PERMITs or DENYspermit;;Specify packets to forwardsremark;;Access list entry comment";
            }
          }
        }
      }
    }
    container crypto {
      tailf:ncs-device-type "cli-ned";
      tailf:display-when "not(../../ncs:module) or ../../ncs:module[ncs:name='tailf-ned-cisco-ios']";
      tailf:info
        "Encryption module";
      container pki {
        tailf:info
          "Public Key components";
        list trustpoint {
          tailf:info
            "Define a CA trustpoint";
          key "id";
          leaf id {
            type string {
              tailf:info
                "WORD;;CA Server Name";
            }
          }
          container enrollment {
            tailf:info
              "Enrollment parameters";
            leaf http-proxy {
              tailf:info
                "HTTP proxy server for enrollment";
              type string {
                tailf:info
                  "WORD;;host-name";
              }
            }
            container mode {
              tailf:info
                "Mode supported by the Certificate Authority";
              leaf ra {
                tailf:info
                  "Registration Authority mode";
                type empty;
              }
            }
            leaf profile {
              tailf:info
                "Specify an profile for enrollment";
              type string {
                tailf:info
                  "WORD;;Profile name";
              }
            }
            container retry {
              tailf:info
                "Polling parameters";
              leaf count {
                tailf:info
                  "How many times to poll CA for our certificate";
                type uint8 {
                  tailf:info
                    "<1-100>;;Number of times to poll a CA for a certificate";
                  range "1..100";
                }
              }
              leaf period {
                tailf:info
                  "How long to wait between requests to CA for our certificate";
                type uint8 {
                  tailf:info
                    "<1-60>;;Period in minutes between attempts to contact a CA";
                  range "1..60";
                }
              }
            }
            leaf selfsigned {
              tailf:info
                "Generate a Self Signed Certificate";
              type empty;
            }
            container terminal {
              tailf:info
                "Enroll via the terminal (cut-and-paste)";
              presence "true";
              leaf pem {
                tailf:info
                  "Include PEM encapsulation boundaries";
                type empty;
              }
            }
            leaf url {
              tailf:info
                "CA server enrollment URL";
              type string {
                tailf:info
                  "WORD;;HTTP URL";
              }
            }
          }
          leaf revocation-check {
            tailf:info
              "Revocation checking options";
            type enumeration {
              enum "none";
            }
          }
          leaf rsakeypair {
            tailf:info
              "Specify rsakeypair for this identity";
            type string;
          }
          leaf subject-name {
            tailf:info
              "Subject Name";
            type string;
          }
        }
        container certificate {
          tailf:info
            "Actions on certificates";
          list chain {
            tailf:info
              "Identify certificates";
            tailf:cli-mode-name "config-cert-chain";
            key "name";
            leaf name {
              type string {
                tailf:info
                  "WORD;;CA Server Name";
              }
            }
            list certificate {
              tailf:info
                "Certificate issued by the CA";
              tailf:cli-suppress-mode;
              tailf:cli-delete-when-empty;
              key "serial";
              leaf serial {
                type string {
                  tailf:info
                    "WORD;;Certificate serial number";
                  pattern '[0-9]+';
                }
              }
              leaf certtype {
                tailf:cli-drop-node-name;
                tailf:cli-prefix-key;
                type enumeration {
                  enum "ca" {
                    tailf:info
                      "CA certificate";
                  }
                  enum "ra-encrypt" {
                    tailf:info
                      "RA encryption certificate";
                  }
                  enum "ra-general" {
                    tailf:info
                      "RA general purpose certificate";
                  }
                  enum "ra-sign" {
                    tailf:info
                      "RA signing certificate";
                  }
                  enum "rollover" {
                    tailf:info
                      "Shadow rollover certificate";
                  }
                  enum "self-signed" {
                    tailf:info
                      "Self-signed certificate";
                  }
                }
              }
              leaf cert {
                tailf:cli-drop-node-name;
                type string;
              }
            }
          }
        }
        container token {
          tailf:info
            "Configure cryptographic token";
          list token-name {
            tailf:cli-suppress-mode;
            tailf:cli-delete-when-empty;
            tailf:cli-drop-node-name;
            tailf:cli-compact-syntax;
            key "name";
            leaf name {
              type string {
                tailf:info
                  "WORD;;token name";
              }
            }
            uses crypto-pki-token-grouping;
          }
        }
        container default {
          tailf:info
            "set default values for tokens";
          uses crypto-pki-token-grouping;
        }
      }
    }
    container mpls {
      tailf:ncs-device-type "cli-ned";
      tailf:display-when "not(../../ncs:module) or ../../ncs:module[ncs:name='tailf-ned-cisco-ios']";
      tailf:info
        "Configure MPLS parameters";
      container atm {
        tailf:info
          "Configure ATM options";
        leaf disable-headend-vc {
          tailf:info
            "Dedicated lsc capability: In this mode headend Tag VCs are disabled.";
          type empty;
        }
      }
      leaf cos-map {
        tailf:info
          "Configure MPLS CoS ATM Multi-VC CoS Map";
        tailf:cli-full-command;
        type uint8 {
          range "1..255" {
            tailf:info
              "<1-255>;;cos-map number";
          }
        }
      }
      container ip {
        tailf:info
          "Dynamic MPLS forwarding for IP";
        leaf default-route {
          tailf:info
            "Allow MPLS forwarding for ip default route";
          tailf:cli-full-command;
          type empty;
        }
        container conf {
          tailf:cli-no-keyword;
          tailf:cli-drop-node-name;
          leaf propagate-ttl {
            tailf:cli-boolean-no;
            type boolean;
            default "true";
          }
        }
        container conf-arg {
          tailf:cli-drop-node-name;
          container propagate-ttl {
            tailf:cli-incomplete-command;
            tailf:cli-incomplete-no;
            leaf forwarded {
              tailf:cli-boolean-no;
              tailf:cli-show-with-default;
              type boolean;
            }
          }
        }
        container ttl-expiration {
          tailf:info
            "Control MPLS TTL expiration behavior";
          leaf pop {
            tailf:info
              "Popping labels on TTL expiration";
            type uint8 {
              range "1..6";
              tailf:info
                "<1-6>;;Popping all labels if original packet has less than N labels";
            }
          }
        }
      }
      container label {
        tailf:info
          "Label properties";
        container atm {
          tailf:info
            "Configure ATM options";
          leaf disable-headend-vc {
            tailf:info
              "Dedicated lsc capability: In this mode headend Tag VCs are disabled.";
            type empty;
          }
        }
        leaf protocol {
          tailf:info
            "Set platform default label distribution protocol";
          tailf:cli-full-command;
          type enumeration {
            enum "ldp" {
              tailf:code-name "label_ldp";
              tailf:info
                "Use LDP (default)";
            }
            enum "tdp:" {
              tailf:code-name "label_tdp";
              tailf:info
                "Use TDP";
            }
          }
          default "ldp";
        }
        container range {
          tailf:info
            "Label range";
          tailf:cli-sequence-commands;
          tailf:cli-compact-syntax;
          leaf min {
            tailf:cli-drop-node-name;
            tailf:cli-incomplete-command;
            type uint32 {
              range "16..1048575";
              tailf:info
                "<16-1048575>  Minimum label value";
            }
          }
          leaf max {
            tailf:cli-drop-node-name;
            type uint32 {
              range "16..1048575";
              tailf:info
                "<16-1048575>  Maximum label value";
            }
          }
        }
      }
      container ldp {
        tailf:info
          "Label Distribution Protocol";
        container enable {
          tailf:cli-drop-node-name;
          leaf advertise-labels {
            tailf:cli-boolean-no;
            tailf:cli-trim-default;
            tailf:cli-show-no;
            type boolean;
            default "true";
          }
        }
        container enable2 {
          tailf:cli-drop-node-name;
          container advertise-labels {
            tailf:cli-incomplete-command;
            tailf:cli-incomplete-no;
            tailf:info
              "Label advertisements";
            container for {
              tailf:info
                "Access-list specifying controls on destination prefixes";
              tailf:cli-sequence-commands;
              tailf:cli-compact-syntax;
              leaf from {
                tailf:cli-drop-node-name;
                type string {
                  tailf:info
                    "WORD;;IP access-list for destination prefixes; name or number (1-99)";
                }
              }
              leaf to {
                tailf:info
                  "Access-list specifying controls on LDP peers";
                type string {
                  tailf:info
                    "WORD;;IP access-list for LDP peers; name or number (1-99)";
                }
              }
            }
            container interface {
              tailf:info
                "Advertise /32 interface address";
              list FastEthernet {
                tailf:info
                  "FastEthernet IEEE 802.3";
                tailf:cli-allow-join-with-key {
                  tailf:cli-display-joined;
                }
                tailf:cli-suppress-mode;
                tailf:cli-delete-when-empty;
                key "name";
                leaf name {
                  type string;
                  tailf:non-strict-leafref {
                    path "/ncs:devices/ncs:device/ncs:config/ios:interface/FastEthernet/name" {
                      tailf:xpath-root 3;
                    }
                  }
                }
              }
            }
            leaf oldstyle {
              tailf:info
                "Use old style (TDP) method for matching prefix acl";
              tailf:cli-full-command;
              type empty;
            }
          }
        }
        container atm {
          tailf:info
            "Configure ATM MPLS options";
          leaf control-mode {
            tailf:info
              "Select LSP setup control mode for MPLS VCs";
            tailf:cli-full-command;
            type enumeration {
              enum "independent" {
                tailf:info
                  "Independent Downstream on Demand Label VC setup";
              }
              enum "ordered" {
                tailf:info
                  "Ordered Dowstream on Demand Label VC setup";
              }
            }
            default "ordered";
            tailf:cli-trim-default;
          }
          leaf vc-merge {
            tailf:info
              "Select VC merge capability";
            tailf:cli-full-command;
            tailf:cli-boolean-no;
            tailf:cli-trim-default;
            type boolean;
            default "true";
          }
        }
        container backoff {
          tailf:info
            "Set LDP session backoff parameters";
          tailf:cli-sequence-commands;
          tailf:cli-compact-syntax;
          leaf initial {
            tailf:cli-drop-node-name;
            tailf:cli-incomplete-command;
            type uint32 {
              tailf:info
                "<5-2147483>;;Initial session backoff time (seconds)";
              range "5..2147483";
            }
          }
          leaf max {
            tailf:cli-drop-node-name;
            type uint32 {
              tailf:info
                "<5-2147483>;;Maximum session backoff time (seconds)";
              range "5..2147483";
            }
          }
        }
        container discovery {
          tailf:info
            "LDP discovery";
          container hello {
            tailf:info
              "LDP discovery Hello";
            leaf holdtime {
              tailf:info
                "LDP discovery Hello holdtime";
              type uint16 {
                tailf:info
                  "<1-65535>;;Holdtime in seconds";
                range "1..65535";
              }
            }
            leaf interval {
              tailf:info
                "LDP discovery Hello interval";
              tailf:cli-full-command;
              type uint16 {
                tailf:info
                  "<1-65535>;;Hello interval in seconds";
                range "1..65535";
              }
            }
          }
          container targeted-hello {
            tailf:info
              "LDP discovery Targeted Hello";
            container accept {
              tailf:info
                "Accept targeted hellos";
              presence "Accept targeted hellos";
              leaf from {
                tailf:info
                  "Access list to specify acceptable targeted hello sources";
                type string {
                  tailf:info
                    "WORD;;IP access-list for acceptable targeted hello sources";
                }
              }
            }
            leaf holdtime {
              tailf:info
                "LDP discovery Hello holdtime";
              type uint16 {
                tailf:info
                  "<1-65535>;;Holdtime in seconds";
                range "1..65535";
              }
            }
            leaf interval {
              tailf:info
                "LDP discovery Hello interval";
              tailf:cli-full-command;
              type uint16 {
                tailf:info
                  "<1-65535>;;Hello interval in seconds";
                range "1..65535";
              }
            }
          }
        }
        container explicit-null {
          tailf:info
            "Advertise Explicit Null label in place of Implicit Null";
          presence "Advertise Explicit Null label in place of Implicit Null";
          leaf for {
            tailf:info
              "Access-list specifying controls on destination prefixes";
            type string {
              tailf:info
                "WORD;;IP access-list for destination prefixes; name or number (1-99)";
            }
          }
          leaf to {
            tailf:info
              "Access-list specifying controls on LDP peers";
            type string {
              tailf:info
                "WORD;;IP access-list for LDP peers; name or number (1-99)";
            }
          }
        }
        container graceful-restart {
          tailf:info
            "Configure Graceful Restart timers";
          presence "Configure Graceful Restart timers";
          container timers {
            tailf:info
              "Configure Graceful Restart timers";
            leaf forwarding-holding {
              tailf:info
                "Forwarding State Holding time";
              tailf:cli-full-command;
              type uint16 {
                tailf:info
                  "<30-600>;;seconds";
                range "30..600";
              }
            }
            leaf max-recovery {
              tailf:info
                "Max-Recovery time";
              tailf:cli-full-command;
              type uint16 {
                tailf:info
                  "<15-600>;;seconds";
                range "15..600";
              }
            }
            leaf neighbor-liveness {
              tailf:info
                "Neighbor-Liveness time";
              tailf:cli-full-command;
              type uint16 {
                range "5..600";
                tailf:info
                  "<5-300>;;seconds";
              }
            }
          }
        }
        leaf holdtime {
          tailf:info
            "LDP session holdtime";
          tailf:cli-full-command;
          type uint32 {
            tailf:info
              "<15-2147483>;;Holdtime in seconds";
            range "15..2147483";
          }
        }
        container logging {
          tailf:info
            "Enable LDP logging";
          leaf neighbor-changes {
            tailf:info
              "Log LDP neighbor state changes";
            type empty;
          }
        }
        leaf loop-detection {
          tailf:info
            "Enable LDP Loop Detection";
          tailf:cli-full-command;
          type empty;
        }
        leaf maxhops {
          tailf:info
            "Limit hop count for LDP LSP setup";
          tailf:cli-full-command;
          type uint8 {
            range "0..255";
            tailf:info
              "<1-255>;;Maximum hop count value";
          }
        }
        list neighbor {
          tailf:info
            "Configure neighbor parameters";
          tailf:cli-suppress-mode;
          tailf:cli-delete-when-empty;
          key "address";
          leaf address {
            type inet:ipv4-address {
              tailf:info
                "A.B.C.D;;IP address for LDP neighbor";
            }
          }
          leaf implicit-withdraw {
            tailf:info
              "Enable LDP Implicit Withdraw Label";
            tailf:cli-full-command;
            type empty;
          }
          container lables {
            tailf:info
              "Configure label binding exchange controls";
            leaf accept {
              tailf:info
                "Specify label bindings to accept";
              type string {
                tailf:info
                  "WORD;;IP access-list for LDP peers; name or number (1-99)";
              }
            }
          }
          container password {
            tailf:info
              "Set a password";
            tailf:cli-compact-syntax;
            leaf enctype {
              tailf:cli-drop-node-name;
              tailf:cli-incomplete-command;
              tailf:cli-reset-container;
              type uint8 {
                range "0..7";
                tailf:info
                  "<0-7>;;Encryption type (0 to disable encryption, 7 for proprietary)";
              }
              default "0";
            }
            leaf text {
              tailf:cli-drop-node-name;
              tailf:cli-full-command;
              tailf:cli-multi-value;
              tailf:cli-reset-container;
              type string {
                pattern '[a-zA-Z].*';
                tailf:info
                  "LINE;;The password";
              }
            }
          }
          container targeted {
            tailf:info
              "Establish targeted session";
            presence "Establish targeted session";
            leaf protocol {
              tailf:cli-drop-node-name;
              type enumeration {
                enum "ldp" {
                  tailf:code-name "target_ldp";
                  tailf:info
                    "User LDP";
                }
                enum "tdp" {
                  tailf:code-name "target_tdp";
                  tailf:info
                    "Use TDP";
                }
              }
            }
          }
        }
        container request-labels {
          tailf:info
            "Access list to specify valid downstream on demand destinations.";
          leaf for {
            tailf:info
              "Access list to specify acceptable downstream on demand destinations";
            type string {
              tailf:info
                "WORD;;IP access-list for destination prefixes; name or number (1-99)";
            }
          }
        }
        container router-id {
          tailf:info
            "Select interface to prefer for LDP identifier address";
          tailf:cli-sequence-commands {
            tailf:cli-reset-siblings;
          }
          tailf:cli-compact-syntax;
          leaf interface {
            tailf:cli-drop-node-name;
            type string {
              tailf:info
                "WORD;;intrace name";
            }
          }
          leaf force {
            tailf:info
              "Forcibly change the LDP router id";
            type empty;
          }
        }
      }
      container prefix-map {
        tailf:info
          "Configure MPLS CoS Tag-VC Multi-VC Prefix Map";
        tailf:cli-sequence-commands;
        tailf:cli-compact-syntax;
        leaf nr {
          tailf:cli-drop-node-name;
          tailf:cli-incomplete-command;
          type uint8 {
            range "1..255";
            tailf:info
              "<1-255>;;prefix-map number";
          }
        }
        leaf access-list {
          tailf:info
            "Configure access-list for this prefix-map";
          tailf:cli-incomplete-command;
          type uint8 {
            range "1..255";
            tailf:info
              "<1-255>;;access-list number";
          }
        }
        leaf cos-map {
          tailf:info
            "Configure cos-map for this prefix-map";
          type uint8 {
            range "1..255";
            tailf:info
              "<1-255>;;cos-map number";
          }
        }
      }
      container traffic-eng {
        tailf:info
          "Configure Traffic Engineering parameters";
        container auto-bw {
          tailf:info
            "auto-bw parameters";
          container timers {
            tailf:info
              "Enable auto-bw Timers Collection and Application";
            presence "Enable auto-bw Timers Collection and Application";
            leaf frequency {
              tailf:info
                "Interval between auto-bw data collection";
              type uint32 {
                tailf:info
                  "<1-604800>;;seconds between auto-bw";
                range "1..604800";
              }
            }
          }
        }
        container link-management {
          tailf:info
            "Link Management configuration";
          container timers {
            tailf:info
              "Link Management timers configuration";
            leaf bandwidth-hold {
              tailf:info
                "Link Management bandwidth hold timer";
              tailf:cli-full-command;
              type uint16 {
                tailf:info
                  "<1-300>;;seconds";
                range "1..300";
              }
            }
            leaf periodic-flooding {
              tailf:info
                "Link Management periodic flooding interval";
              tailf:cli-full-command;
              type uint16 {
                tailf:info
                  "<0-3600>;;seconds";
                range "0..3600";
              }
            }
          }
        }
        container logging {
          tailf:info
            "Trap logging configuration";
          container lsp {
            tailf:info
              "LSP-specific traps logging configuration";
            container path-errors {
              tailf:info
                "Log LSP Path Error traps";
              presence "Log LSP Path Error traps";
              leaf access-list {
                tailf:cli-drop-node-name;
                type access-list-type;
              }
            }
            container preemption {
              tailf:info
                "Log LSP Preemption traps";
              presence "Log LSP Preemption traps";
              leaf access-list {
                tailf:cli-drop-node-name;
                type access-list-type;
              }
            }
            container reservation-errors {
              tailf:info
                "Log LSP Reservation Error traps";
              presence "Log LSP Reservation Error traps";
              leaf access-list {
                tailf:cli-drop-node-name;
                type access-list-type;
              }
            }
            container setups {
              tailf:info
                "Log LSP Establishment Traps";
              presence "Log LSP Establishment Traps";
              leaf access-list {
                tailf:cli-drop-node-name;
                type access-list-type;
              }
            }
            container teardowns {
              tailf:info
                "Log LSP Teardown Traps";
              presence "Log LSP Teardown Traps";
              leaf access-list {
                tailf:cli-drop-node-name;
                type access-list-type;
              }
            }
          }
          container tunnel {
            tailf:info
              "Tunnel-specific traps logging configuration";
            container lsp-selection {
              tailf:info
                "Log Tunnel LSP Selection traps";
              presence "Log Tunnel LSP Selection traps";
              leaf access-list {
                tailf:cli-drop-node-name;
                type access-list-type;
              }
            }
            container path {
              tailf:info
                "Log Tunnel Path-related traps";
              container change {
                tailf:info
                  "Log Tunnel Path change traps";
                presence "Log Tunnel Path change traps";
                leaf access-list {
                  tailf:cli-drop-node-name;
                  type access-list-type;
                }
              }
            }
          }
        }
        container path-selection {
          tailf:info
            "Path Selection Configuration";
          leaf metric {
            tailf:info
              "Metric Type Configuration";
            tailf:cli-full-command;
            type enumeration {
              enum "igp" {
                tailf:info
                  "Use IGP metric";
              }
              enum "te" {
                tailf:info
                  "User TE metric";
              }
            }
          }
          container overload {
            tailf:info
              "Overload Node Configuration";
            container allow {
              tailf:info
                "Allow overloaded nodes in CSPFs";
              tailf:cli-sequence-commands;
              leaf head {
                tailf:info
                  "Allow overloaded head node in TE CSPF";
                tailf:cli-optional-in-sequence;
                tailf:cli-reset-container;
                type empty;
              }
              leaf middle {
                tailf:info
                  "Allow overloaded middle node in TE CSPF";
                tailf:cli-optional-in-sequence;
                tailf:cli-reset-container;
                type empty;
              }
              leaf tail {
                tailf:info
                  "Allow overloaded middle node in TE CSPF";
                tailf:cli-optional-in-sequence;
                tailf:cli-reset-container;
                type empty;
              }
            }
          }
        }
        container reoptimize {
          tailf:info
            "Reoptimization parameters";
          container events {
            tailf:info
              "Reoptimization triggers";
            leaf link-up {
              tailf:info
                "Reoptimize tunnels on link up events";
              type empty;
            }
          }
          container timers {
            tailf:info
              "Reoptimization timers";
            container delay {
              tailf:info
                "Delay reoptimization action";
              leaf cleanup {
                tailf:info
                  "Delay cleanup of reoptimized LSP";
                tailf:cli-full-command;
                type uint8 {
                  range "0..60";
                  tailf:info
                    "<0-60>;;seconds to delay cleanup of replaced tunnel LSP";
                }
              }
              leaf installation {
                tailf:info
                  "Delay replacement of current LSP by reoptimized LSP";
                tailf:cli-full-command;
                type uint16 {
                  range "0..3600";
                  tailf:info
                    "<0-3600>;;seconds to delay replacement of tunnel LSP";
                }
              }
            }
            leaf frequency {
              tailf:info
                "Interval between reoptimization scans";
              tailf:cli-full-command;
              type uint32 {
                tailf:info
                  "<0-604800>;;seconds between reoptimizations (0 disables reoptimization)";
                range "0..604800";
              }
            }
          }
        }
        container signalling {
          tailf:info
            "Traffic Engineering Signalling Parameters";
          container advertise {
            tailf:info
              "Signalling advertisement parameters";
            container implicit-null {
              tailf:info
                "Use MPLS encoding for Implicit-Null Label in signalling messages";
              presence "Use MPLS encoding for Implicit-Null Label in signalling messages";
              leaf nr {
                tailf:cli-drop-node-name;
                type uint8 {
                  range "1..99";
                  tailf:info
                    "<1-99>;;Number of IP access-list to determine applicable signalling peers";
                }
              }
            }
          }
          container forwarding {
            tailf:info
              "Control interaction of LSP signalling and LFIB maintenance";
            leaf sync {
              tailf:info
                "Program linecard LFIBs before signalling LSP label upstream";
              type empty;
            }
          }
          container restart {
            tailf:info
              "Signalling restart parameters";
            container neighbors {
              tailf:info
                "Identify signalling restart capable neighbors";
              presence "Identify signalling restart capable neighbors";
              leaf nr {
                tailf:cli-drop-node-name;
                type uint8 {
                  range "1..99";
                  tailf:info
                    "<1-99>;;Number of IP access-list to determine applicable signalling peers";
                }
              }
            }
          }
        }
        container topology {
          tailf:info
            "Topology Database Configuration";
          container holddown {
            tailf:info
              "Topology Database hold down timers";
            leaf sigerr {
              tailf:info
                "Link hold down time for signalling errors";
              type uint16 {
                range "0..300";
                tailf:info
                  "<0-300>;;Hold down time in seconds";
              }
            }
          }
        }
        leaf tunnels {
          tailf:info
            "Traffic Engineering tunnels";
          tailf:cli-full-command;
          type empty;
        }
      }
    }
    container router {
      tailf:ncs-device-type "cli-ned";
      tailf:display-when "not(../../ncs:module) or ../../ncs:module[ncs:name='tailf-ned-cisco-ios']";
      tailf:info
        "Enable a routing process";
      list bgp {
        tailf:info
          "Border Gateway Protocol (BGP)";
        tailf:cli-mode-name "config-router";
        tailf:cli-diff-dependency "/ios:vrf/definition" {
          tailf:xpath-root 3;
        }
        tailf:cli-diff-dependency "/ios:ip/vrf" {
          tailf:xpath-root 3;
        }
        key "as-no";
        max-elements 1;
        leaf as-no {
          tailf:cli-suppress-range;
          type uint16 {
            range "1..65535";
            tailf:info
              "<1-65535>;;Autonomous system number";
          }
        }
        uses bgp-address-family-grouping;
        container address-family {
          tailf:info
            "Enter Address Family command mode";
          container no-vrf {
            tailf:cli-drop-node-name;
            list ipv4 {
              tailf:info
                "Address family";
              tailf:cli-full-command;
              tailf:cli-delete-when-empty;
              tailf:cli-exit-command "exit-address-family" {
                tailf:info
                  "Exit from Address Family configuration mode";
              }
              key "unicast-multicast";
              leaf unicast-multicast {
                type enumeration {
                  enum "unicast" {
                    tailf:code-name "ipv4_unicast";
                    tailf:info
                      "Address Family modifier";
                  }
                  enum "multicast" {
                    tailf:code-name "ipv4_multicast";
                    tailf:info
                      "Address Family modifier";
                  }
                  enum "mdt" {
                    tailf:info
                      "IPv4 multicast distribution tree (MDT)";
                  }
                  enum "tunnel" {
                    tailf:info
                      "IPv4 tunnel address prefixes.";
                  }
                  enum "labeled-unicast" {
                    tailf:info
                      "IPv4 labeled-unicast address prefixes";
                  }
                }
                tailf:key-default "unicast";
              }
              uses bgp-address-family-grouping;
            }
          }
          container with-vrf {
            tailf:cli-drop-node-name;
            list ipv4 {
              tailf:info
                "Address family";
              tailf:cli-suppress-mode;
              tailf:cli-delete-when-empty;
              tailf:cli-incomplete-command;
              key "unicast-multicast";
              leaf unicast-multicast {
                type enumeration {
                  enum "unicast" {
                    tailf:code-name "ipv4_unicast";
                    tailf:info
                      "Address Family modifier";
                  }
                  enum "multicast" {
                    tailf:code-name "ipv4_multicast";
                    tailf:info
                      "Address Family modifier";
                  }
                  enum "mdt" {
                    tailf:info
                      "IPv4 multicast distribution tree (MDT)";
                  }
                  enum "tunnel" {
                    tailf:info
                      "IPv4 tunnel address prefixes.";
                  }
                  enum "labeled-unicast" {
                    tailf:info
                      "IPv4 labeled-unicast address prefixes";
                  }
                }
                tailf:key-default "unicast";
              }
              list vrf {
                tailf:cli-mode-name "config-router-af";
                tailf:cli-full-command;
                tailf:cli-diff-dependency "/ios:ip/vrf" {
                  tailf:xpath-root 3;
                }
                tailf:cli-diff-dependency "/ios:vrf/definition" {
                  tailf:xpath-root 3;
                }
                tailf:cli-exit-command "exit-address-family" {
                  tailf:info
                    "Exit from Address Family configuration mode";
                }
                key "name";
                leaf name {
                  type string {
                    tailf:info
                      "WORD;;VPN Routing/Forwarding instance name";
                  }
                }
                uses bgp-address-family-grouping;
              }
            }
          }
          list ipv6 {
            tailf:info
              "Address family";
            tailf:cli-suppress-mode;
            tailf:cli-delete-when-empty;
            tailf:cli-incomplete-command;
            key "unicast-multicast";
            leaf unicast-multicast {
              type enumeration {
                enum "unicast" {
                  tailf:code-name "ipv6_unicast";
                  tailf:info
                    "Address Family modifier";
                }
                enum "multicast" {
                  tailf:code-name "ipv6_multicast";
                  tailf:info
                    "Address Family modifier";
                }
              }
              tailf:key-default "unicast";
            }
            list vrf {
              tailf:cli-full-command;
              tailf:cli-diff-dependency "/ios:vrf/definition" {
                tailf:xpath-root 3;
              }
              tailf:cli-exit-command "exit-address-family" {
                tailf:info
                  "Exit from Address Family configuration mode";
              }
              key "name";
              leaf name {
                type string {
                  tailf:info
                    "WORD;;VPN Routing/Forwarding instance name";
                }
              }
              uses bgp-address-family-grouping;
            }
            uses bgp-address-family-grouping;
          }
          list vpnv4 {
            tailf:info
              "Address family";
            tailf:cli-exit-command "exit-address-family" {
              tailf:info
                "Exit from Address Family configuration mode";
            }
            key "unicast-multicast";
            leaf unicast-multicast {
              type enumeration {
                enum "unicast" {
                  tailf:code-name "vpnv4_unicast";
                  tailf:info
                    "Address Family modifier";
                }
              }
              tailf:key-default "unicast";
            }
            uses bgp-address-family-grouping;
          }
          list vpnv6 {
            tailf:info
              "Address family";
            tailf:cli-exit-command "exit-address-family" {
              tailf:info
                "Exit from Address Family configuration mode";
            }
            key "unicast-multicast";
            leaf unicast-multicast {
              type enumeration {
                enum "unicast" {
                  tailf:code-name "vpnv6_unicast";
                  tailf:info
                    "Address Family modifier";
                }
              }
              tailf:key-default "unicast";
            }
            uses bgp-address-family-grouping;
          }
          list nsap {
            tailf:info
              "Address family";
            tailf:cli-exit-command "exit-address-family" {
              tailf:info
                "Exit from Address Family configuration mode";
            }
            key "unicast-multicast";
            leaf unicast-multicast {
              type enumeration {
                enum "unicast" {
                  tailf:code-name "nsap_unicast";
                  tailf:info
                    "Address Family modifier";
                }
              }
              tailf:key-default "unicast";
            }
            uses bgp-address-family-grouping;
          }
        }
        container template {
          tailf:info
            "Enter template command mode";
          list peer-policy {
            tailf:info
              "Template configuration for policy parameters";
            tailf:cli-exit-command "exit-peer-policy" {
              tailf:info
                "Exit from template configuration mode";
            }
            key "name";
            leaf name {
              type string {
                tailf:info
                  "WORD;;Name of peer-policy template";
              }
            }
          }
          list peer-session {
            tailf:info
              "Template configuration for session parameters";
            tailf:cli-exit-command "exit-peer-session" {
              tailf:info
                "Exit from template configuration mode";
            }
            key "name";
            leaf name {
              type string {
                tailf:info
                  "WORD;;Name of peer-session template";
              }
            }
          }
        }
      }
      list ospfv3 {
        tailf:cli-mode-name "config-router";
        tailf:info
          "OSPFv3";
        key "id";
        leaf id {
          tailf:cli-suppress-range;
          type uint16 {
            range "1..65535";
            tailf:info
              "<1-65535>;;Process ID";
          }
        }
        uses ospf-ospfv3-common-grouping;
        container address-family {
          tailf:info
            "Enter Address Family command mode";
          container ipv4 {
            tailf:info
              "Address family";
            container unicast {
              tailf:info
                "Address Family Modifier";
              tailf:cli-add-mode;
              tailf:cli-mode-name "config-router-af";
              tailf:cli-full-command;
              tailf:cli-exit-command "exit-address-family" {
                tailf:info
                  "Exit from Address Family configuration mode";
              }
              uses ospf-ospfv3-common-grouping;
              uses ospf-ospfv3-common-address-family-grouping;
            }
          }
          container ipv6 {
            tailf:info
              "Address family";
            container unicast {
              tailf:cli-add-mode;
              tailf:cli-mode-name "config-router-af";
              tailf:info
                "Address Family Modifier";
              tailf:cli-full-command;
              tailf:cli-exit-command "exit-address-family" {
                tailf:info
                  "Exit from Address Family configuration mode";
              }
              uses ospf-ospfv3-common-grouping;
              uses ospf-ospfv3-common-address-family-grouping;
            }
          }
        }
      }
      list ospf {
        tailf:cli-mode-name "config-router";
        tailf:info
          "Open Shortest Path First (OSPF)";
        key "id";
        leaf id {
          tailf:cli-suppress-range;
          type uint16 {
            range "1..65535";
            tailf:info
              "<1-65535>;;Process ID";
          }
        }
        list vrf {
          tailf:info
            "VPN Routing/Forwarding Instance";
          tailf:cli-full-command;
          tailf:cli-diff-dependency "/ios:ip/vrf" {
            tailf:xpath-root 3;
          }
          tailf:cli-diff-dependency "/ios:vrf/definition" {
            tailf:xpath-root 3;
          }
          key "name";
          leaf name {
            type string {
              tailf:info
                "WORD;;VPN Routing/Forwarding Instance (VRF) name";
            }
          }
        }
        container non-vrf {
          tailf:cli-full-command;
          tailf:cli-drop-node-name;
          uses ospf-ospfv3-common-grouping;
          uses ospf-ospfv3-common-address-family-grouping;
          container capability {
            tailf:info
              "Enable specific OSPF feature";
            leaf capability-type {
              tailf:cli-drop-node-name;
              type enumeration {
                enum "lls" {
                  tailf:info
                    "Link-local Signaling (LLS) support";
                }
                enum "opaque" {
                  tailf:info
                    "Opaque LSA";
                }
                enum "transit" {
                  tailf:info
                    "Transit Area";
                }
              }
            }
          }
          container compatible {
            tailf:info
              "OSPF compatibility list";
            leaf rfc1583 {
              tailf:info
                "compatible with RFC 1583";
              type empty;
            }
          }
          uses distribute-list-grouping;
          container domain-id {
            tailf:info
              "OSPF domain-id";
            choice domain-id-choice {
              leaf ip-format {
                tailf:cli-drop-node-name;
                type inet:ipv4-address {
                  tailf:info
                    "A.B.C.D;;OSPF domain ID in IP address format";
                }
              }
              container ip-format-secondary {
                tailf:cli-drop-node-name;
                tailf:cli-compact-syntax;
                tailf:cli-sequence-commands;
                leaf ip {
                  tailf:cli-drop-node-name;
                  type inet:ipv4-address {
                    tailf:info
                      "A.B.C.D;;OSPF domain ID in IP address format";
                  }
                }
                leaf secondary {
                  tailf:info
                    "Secondary Domain-ID";
                  type empty;
                }
              }
              leaf Null {
                tailf:info
                  "Null Domain-ID";
                tailf:cli-full-command;
                type empty;
              }
              container type {
                tailf:info
                  "OSPF domain ID type in Hex format";
                tailf:cli-sequence-commands;
                tailf:cli-compact-syntax;
                leaf type-leaf {
                  tailf:cli-drop-node-name;
                  tailf:cli-incomplete-command;
                  type enumeration {
                    enum "0005" {
                      tailf:info
                        "Type 0x0005";
                    }
                    enum "0105" {
                      tailf:info
                        "Type 0x0105";
                    }
                    enum "0205" {
                      tailf:info
                        "Type 0x0205";
                    }
                    enum "8005" {
                      tailf:info
                        "Type 0x8005";
                    }
                  }
                }
                leaf value {
                  tailf:info
                    "OSPF domain ID value in Hex format";
                  type string {
                    tailf:info
                      "Hex-data;;OSPF domain ID ext. community value in Hex";
                    pattern '[0-9a-fA-F]{12}';
                  }
                }
              }
            }
          }
          leaf domain-tag {
            tailf:info
              "OSPF domain-tag";
            tailf:cli-full-command;
            type uint32 {
              range "1 .. 4294967295";
              tailf:info
                "<1-4294967295>;;OSPF domain tag - 32-bit value";
            }
          }
          container ignore {
            tailf:info
              "Do not complain about specific event";
            container lsa {
              tailf:info
                "Do not complain upon receiving LSA of the specified type";
              leaf mospf {
                tailf:info
                  "MOSPF Type 6 LSA";
                type empty;
              }
            }
          }
          leaf ispf {
            tailf:info
              "Enable incremental SPF computation";
            tailf:cli-full-command;
            type empty;
          }
          container limit {
            tailf:info
              "Limit a specific OSPF feature";
            tailf:cli-compact-syntax;
            container retransmissions {
              tailf:info
                "LS update, DBD, and LS request retransmissions";
              leaf non-dc {
                tailf:info
                  "Non-demand-circuit retransmissions";
                type limit-dc-non-dc-type;
              }
              leaf dc {
                tailf:info
                  "Demand circuit retransmissions";
                type limit-dc-non-dc-type;
              }
            }
          }
          container local-rib-criteria {
            tailf:info
              "Enable or disable usage of local RIB as route criteria";
            tailf:cli-compact-syntax;
            leaf forwarding-address {
              tailf:info
                "Local RIB used to validate external/NSSA forwarding addresses";
              type empty;
            }
            leaf inter-area-summary {
              tailf:info
                "Local RIB used as criteria for inter-area summaries";
              type empty;
            }
            leaf nssa-translation {
              tailf:info
                "Local RIB used as criteria for NSSA translation";
              type empty;
            }
          }
          container max-metric {
            tailf:info
              "Set maximum metric";
            container router-lsa {
              tailf:info
                "Maximum metric in self-originated router-LSAs";
              presence "Maximum metric in self-originated router-LSAs";
              container external-lsa {
                tailf:info
                  "Override external-lsa metric with max-metric value";
                presence "Override external-lsa metric with max-metric value";
                tailf:cli-flatten-container;
                leaf metric {
                  tailf:cli-drop-node-name;
                  type uint32 {
                    range "1 .. 16777215";
                    tailf:info
                      "<1-16777215>;;Overriding metric in external-LSAs (default 16711680)";
                  }
                }
              }
              leaf include-stub {
                tailf:info
                  "Set maximum metric for stub links in router-LSAs";
                type empty;
              }
              container on-startup {
                tailf:info
                  "Set maximum metric temporarily after reboot";
                presence "Set maximum metric temporarily after reboot";
                tailf:cli-flatten-container;
                choice time-wait-for-bgp-choice {
                  leaf time {
                    tailf:cli-drop-node-name;
                    type uint32 {
                      range "5 .. 86400";
                      tailf:info
                        "<5-86400>;;Time, in seconds, router-LSAs are originated with max-metric";
                    }
                  }
                  leaf wait-for-bgp {
                    tailf:info
                      "Let BGP decide when to originate router-LSA with normal metric";
                    type empty;
                  }
                }
              }
              container summary-lsa {
                tailf:info
                  "Override summary-lsa metric with max-metric value";
                presence "Override summary-lsa metric with max-metric value";
                tailf:cli-flatten-container;
                leaf metric {
                  tailf:cli-drop-node-name;
                  type uint32 {
                    range "1 .. 16777215";
                    tailf:info
                      " <1-16777215>;;Overriding metric in summary-LSAs (default 16711680)";
                  }
                }
              }
            }
          }
          container mpls {
            tailf:info
              "Configure MPLS routing protocol parameters";
            container ldp {
              tailf:info
                "routing protocol commands for MPLS LDP";
              container autoconfig {
                tailf:info
                  "Configure LDP automatic configuration";
                presence "Configure LDP automatic configuration";
                leaf area {
                  tailf:info
                    "Configure an OSPF area to run MPLS LDP";
                  type ospf-area-type;
                }
              }
              container sync {
                tailf:info
                  "Configure LDP-IGP Synchronization";
                presence "Configure LDP-IGP Synchronization";
              }
            }
            container traffic-eng {
              tailf:info
                "routing protocol commands for MPLS Traffic Engineering";
              tailf:cli-compact-syntax;
              leaf multicast-intact {
                tailf:info
                  "MPLS TE and PIM interaction";
                tailf:cli-full-command;
                type empty;
              }
              leaf area {
                tailf:info
                  "configure an ospf area to run MPLS Traffic Engineering";
                tailf:cli-full-command;
                type ospf-area-type;
              }
              container interface {
                tailf:info
                  "MPLS TE interface configuration for this OSPF process";
                tailf:cli-sequence-commands;
                leaf name {
                  tailf:cli-drop-node-name;
                  tailf:cli-incomplete-command;
                  type string {
                    tailf:info
                      "WORD;;Interface name";
                  }
                }
                leaf area {
                  tailf:info
                    "advertise MPLS TE information for this interface into area";
                  type uint32 {
                    tailf:info
                      "<0-0>;;OSPF area ID as a decimal value";
                  }
                }
              }
              container mesh-group-container {
                tailf:cli-drop-node-name;
                tailf:cli-sequence-commands;
                leaf mesh-group {
                  tailf:info
                    "Traffic Engineering Mesh-Group advertisement";
                  tailf:cli-incomplete-command;
                  type uint32 {
                    range "0 .. 4294967295";
                    tailf:info
                      "<0-4294967295>;;Mesh Group Id";
                  }
                }
                leaf interface {
                  tailf:info
                    "Interface";
                  tailf:cli-incomplete-command;
                  type string {
                    tailf:info
                      "WORD;;Interface name";
                  }
                }
                list area {
                  tailf:info
                    "configure flooding scope as area";
                  tailf:cli-suppress-mode;
                  tailf:cli-delete-when-empty;
                  key "id";
                  leaf id {
                    tailf:cli-suppress-range;
                    type ospf-area-type;
                  }
                }
              }
              container router-id {
                tailf:info
                  "Traffic Engineering stable IP address for system";
                leaf interface {
                  tailf:info
                    "Interface";
                  type string {
                    tailf:info
                      "WORD;;Interface name";
                  }
                }
              }
            }
          }
          list neighbor {
            tailf:info
              "Specify a neighbor router";
            tailf:cli-suppress-mode;
            tailf:cli-delete-when-empty;
            key "ip";
            leaf ip {
              type inet:ipv4-address {
                tailf:info
                  "A.B.C.D;;Neighbor address";
              }
            }
            container cost-database-filter-container {
              tailf:cli-drop-node-name;
              tailf:cli-compact-syntax;
              leaf cost {
                tailf:info
                  "OSPF cost for point-to-multipoint neighbor";
                type uint32 {
                  range "1 .. 65535";
                  tailf:info
                    "<1-65535>;;metric";
                }
              }
              container database-filter {
                tailf:info
                  "Filter OSPF LSA during synchronization and flooding for point-to-multipoint neighbor";
                container all {
                  tailf:info
                    "Filter all LSA";
                  tailf:cli-compact-syntax;
                  leaf out {
                    tailf:info
                      "Outgoing LSA";
                    type empty;
                  }
                }
              }
            }
            container poll-interval-priority-container {
              tailf:cli-drop-node-name;
              tailf:cli-compact-syntax;
              leaf poll-interval {
                tailf:info
                  "OSPF dead-router polling interval";
                type uint32 {
                  range "0 .. 65535";
                  tailf:info
                    "<0-65535>;;Seconds";
                }
              }
              leaf priority {
                tailf:info
                  "OSPF priority of non-broadcast neighbor";
                type uint32 {
                  range "0 .. 255";
                  tailf:info
                    "<0-255>;;Priority";
                }
              }
            }
          }
          list network {
            tailf:info
              "Enable routing on an IP network";
            tailf:cli-incomplete-command;
            tailf:cli-suppress-mode;
            tailf:cli-delete-when-empty;
            key "ip mask";
            leaf ip {
              type inet:ipv4-address {
                tailf:info
                  "A.B.C.D;;Network number";
              }
            }
            leaf mask {
              type inet:ipv4-address {
                tailf:info
                  "A.B.C.D;;OSPF wild card bits";
              }
            }
            leaf area {
              tailf:info
                "Set the OSPF area ID";
              type ospf-area-type;
            }
          }
          container nsf {
            tailf:info
              "Non-stop forwarding";
            container cisco {
              tailf:info
                "Cisco Non-stop forwarding";
              container helper {
                tailf:info
                  "helper support";
                presence "helper support";
                leaf disable {
                  tailf:cli-reset-container;
                  tailf:info
                    "disable helper support";
                  type empty;
                }
              }
            }
            container ietf {
              tailf:info
                "IETF graceful restart";
              container helper {
                tailf:info
                  "helper support";
                presence "helper support";
                leaf disable {
                  tailf:cli-reset-container;
                  tailf:cli-delete-container-on-delete;
                  tailf:info
                    "disable helper support";
                  type empty;
                }
                leaf strict-lsa-checking {
                  tailf:info
                    "enable helper strict LSA checking";
                  type empty;
                }
              }
            }
          }
          leaf prefix-suppression {
            tailf:info
              "OSPF prefix suppression";
            tailf:cli-full-command;
            type empty;
          }
          container process-min-time {
            tailf:info
              "Percentage of quantum to be used before releasing CPU";
            leaf percent {
              tailf:info
                "percent";
              type uint32 {
                range "1 .. 100";
                tailf:info
                  "<1-100>;;Minimum CPU quantum";
              }
            }
          }
          container traffic-share {
            tailf:info
              "How to compute traffic share over alternate paths";
            container min {
              tailf:info
                "All traffic shared among min metric paths";
              leaf across-interface {
                tailf:info
                  "Use different interfaces for equal-cost paths";
                type empty;
              }
            }
          }
          leaf shutdown {
            tailf:info
              "Shutdown the OSPF protocol under the current instance";
            tailf:cli-boolean-no;
            type boolean;
          }
          list summary-address {
            tailf:info
              "Configure IP address summaries";
            tailf:cli-suppress-mode;
            tailf:cli-delete-when-empty;
            key "ip wildcard";
            leaf ip {
              type inet:ipv4-address {
                tailf:info
                  "A.B.C.D;;IP summary address";
              }
            }
            leaf wildcard {
              type inet:ipv4-address {
                tailf:info
                  "A.B.C.D;;Summary mask";
              }
            }
            choice tag-no-advertise-choice {
              leaf tag {
                tailf:info
                  "Set tag";
                tailf:cli-full-command;
                type uint32 {
                  range "0 .. 4294967295";
                  tailf:info
                    "<0-4294967295>;;32-bit tag value";
                }
              }
              leaf not-advertise {
                tailf:info
                  "Do not advertise when translating OSPF type-7 LSA";
                type empty;
                tailf:cli-full-command;
              }
            }
          }
        }
      }
      container isis {
        tailf:cli-add-mode;
        tailf:info
          "ISO IS-IS";
        tailf:cli-mode-name "config-router";
        presence "true";
        uses isis-main-grouping;
      }
      container isis-container {
        tailf:cli-drop-node-name;
        list isis {
          tailf:info
            "ISO IS-IS";
          tailf:cli-mode-name "config-router";
          key "area-tag";
          leaf area-tag {
            type string {
              tailf:info
                "WORD;;ISO routing area tag";
            }
          }
          uses isis-main-grouping;
        }
      }
      container rip {
        tailf:cli-add-mode;
        tailf:cli-mode-name "config-router";
        tailf:info
          "Routing Information Protocol (RIP)";
        uses router-rip-grouping;
        container address-family {
          tailf:info
            "Enter Address Family command mode";
          container ipv4 {
            tailf:info
              "Address family";
            container unicast {
              tailf:cli-add-mode;
              tailf:cli-mode-name "config-router-af";
              tailf:info
                "Address Family Modifier";
              tailf:cli-full-command;
              tailf:cli-exit-command "exit-address-family" {
                tailf:info
                  "Exit from Address Family configuration mode";
              }
              uses router-rip-grouping;
            }
            list vrf {
              tailf:info
                "Specify parameters for a VPN Routing/Forwarding instance";
              tailf:cli-full-command;
              tailf:cli-mode-name "config-router-af";
              tailf:cli-diff-dependency "/ios:ip/vrf" {
                tailf:xpath-root 3;
              }
              tailf:cli-diff-dependency "/ios:vrf/definition" {
                tailf:xpath-root 3;
              }
              tailf:cli-exit-command "exit-address-family" {
                tailf:info
                  "Exit from Address Family configuration mode";
              }
              key "name";
              leaf name {
                type string {
                  tailf:info
                    "WORD;;VPN Routing/Forwarding instance name";
                }
              }
              uses address-family-vrf-grouping;
            }
          }
        }
        container default {
          tailf:info
            "Set a command to its defaults";
          container address-family {
            tailf:info
              "Enter Address Family command mode";
            container ipv4 {
              presence "true";
              tailf:info
                "Address family";
              leaf unicast {
                tailf:info
                  "Address Family Modifier";
                type empty;
              }
              list vrf {
                tailf:info
                  "Specify parameters for a VPN Routing/Forwarding instance";
                tailf:cli-suppress-mode;
                tailf:cli-delete-when-empty;
                tailf:cli-diff-dependency "/ios:ip/vrf" {
                  tailf:xpath-root 3;
                }
                tailf:cli-diff-dependency "/ios:vrf/definition" {
                  tailf:xpath-root 3;
                }
                key "name";
                leaf name {
                  type string {
                    tailf:info
                      "WORD;;VPN Routing/Forwarding instance name";
                  }
                }
              }
            }
          }
          uses default-router-rip-grouping;
          container default-information {
            tailf:info
              "Control distribution of default information";
            leaf originate {
              tailf:info
                "Distribute a default route";
              type empty;
            }
          }
          leaf default-metric {
            tailf:cli-full-command;
            tailf:info
              "Set metric of redistributed routes";
            type empty;
          }
          uses distance-grouping;
          uses distribute-list-grouping;
          leaf flash-update-threshold {
            tailf:cli-full-command;
            tailf:info
              "Specify flash update threshold in second";
            type empty;
          }
          leaf input-queue {
            tailf:cli-full-command;
            tailf:info
              "Specify input queue depth";
            type empty;
          }
          uses offset-list-grouping;
          leaf output-delay {
            tailf:cli-full-command;
            tailf:info
              "Interpacket delay for RIP updates";
            type empty;
          }
          uses passive-interface-grouping;
          container redistribute {
            tailf:info
              "Redistribute information from another routing protocol";
            uses default-redistribute-grouping;
          }
          container timers {
            tailf:info
              "Adjust routing timers";
            leaf basic {
              tailf:info
                "Basic routing protocol update timers";
              type empty;
            }
          }
          container traffic-share {
            tailf:info
              "How to compute traffic share over alternate paths";
            container min {
              tailf:info
                "All traffic shared among min metric paths";
              leaf across-interfaces {
                tailf:info
                  "Use different interfaces for equal-cost paths";
                type empty;
              }
            }
          }
          leaf version {
            tailf:cli-full-command;
            tailf:info
              "Set routing protocol version";
            type empty;
          }
        }
      }
    }
    container snmp {
      tailf:ncs-device-type "cli-ned";
      tailf:display-when "not(../../ncs:module) or ../../ncs:module[ncs:name='tailf-ned-cisco-ios']";
      tailf:info
        "Modify non engine SNMP parameters";
      container ifmib {
        tailf:info
          "IF-MIB commands";
        container ifindex {
          tailf:info
            "ifindex persistence";
          leaf persist {
            tailf:info
              "Persist interface indices";
            type empty;
          }
        }
        container ifalias {
          tailf:info
            "ifAlias description option, by default it is limited to 64 character";
          leaf long {
            tailf:info
              "ifAlias description can be up to 256 characters";
            type empty;
          }
        }
      }
      container mib {
        tailf:info
          "MIB commands";
        container bulkstat {
          tailf:info
            "Bulkstat Configuration commands";
          list object-list {
            tailf:info
              "Configure an Object List.";
            tailf:cli-suppress-mode;
            tailf:cli-delete-when-empty;
            key "name";
            leaf name {
              type string {
                tailf:info
                  "WORD;;Name of object list";
              }
            }
          }
        }
        leaf persist {
          tailf:info
            "Persistence for MIBS";
          tailf:cli-full-command;
          type enumeration {
            enum "cbqos" {
              tailf:info
                "CBQOS MIB index persistence";
            }
            enum "circuit" {
              tailf:info
                "Circuit MIB persistence";
            }
          }
        }
      }
    }
    container snmp-server {
      tailf:ncs-device-type "cli-ned";
      tailf:display-when "not(../../ncs:module) or ../../ncs:module[ncs:name='tailf-ned-cisco-ios']";
      tailf:info
        "Modify SNMP engine parameters";
      list community {
        tailf:info
          "Enable SNMP; set community string and access privs";
        tailf:cli-suppress-mode;
        tailf:cli-delete-when-empty;
        tailf:cli-compact-syntax;
        tailf:cli-sequence-commands {
          tailf:cli-reset-siblings;
        }
        key "name";
        leaf name {
          type string {
            tailf:info
              "WORD;;SNMP community string";
          }
        }
        leaf view {
          tailf:info
            "Restrict this community to a named MIB view";
          tailf:cli-optional-in-sequence;
          type string {
            tailf:info
              "WORD;;MIB view to which this community has access";
          }
        }
        choice access-choice {
          leaf RO {
            tailf:info
              "Read-only access with this community string";
            tailf:cli-optional-in-sequence;
            type empty;
          }
          leaf RW {
            tailf:info
              "Read-write access with this community string";
            tailf:cli-optional-in-sequence;
            type empty;
          }
        }
        choice access-list-choice {
          case ipv6 {
            leaf ipv6 {
              tailf:info
                "Specify IPv6 Named Access-List";
              type string {
                tailf:info
                  "WORD;;IPv6 Access-list name";
              }
            }
          }
          case ipv4 {
            leaf access-list-name {
              tailf:cli-drop-node-name;
              type std-acl-type;
            }
          }
        }
      }
      leaf contact {
        tailf:info
          "Text for mib object sysContact";
        tailf:cli-multi-value;
        type string {
          tailf:info
            "LINE;;identification of the contact person for this managed node";
        }
      }
      container enable {
        tailf:info
          "Enable SNMP Traps or Informs";
        choice enable-choice {
          case informs {
            leaf informs {
              tailf:info
                "Enable SNMP Informs";
              type empty;
            }
          }
          case traps {
            container traps {
              tailf:info
                "Enable SNMP Traps";
              leaf aaa_server {
                tailf:info
                  "Enable SNMP AAA Server traps";
                tailf:cli-full-command;
                type empty;
              }
              container alarms {
                tailf:info
                  "Enable SNMP alarms traps";
                tailf:cli-delete-when-empty;
                presence "true";
                leaf informational {
                  type empty;
                }
              }
              container atm {
                tailf:info
                  "Enable SNMP atm traps";
                container pvc {
                  tailf:info
                    "Enable SNMP atm pvc traps";
                  tailf:cli-sequence-commands;
                  tailf:cli-delete-when-empty;
                  presence "true";
                  container extension {
                    tailf:info
                      "Enable SNMP atm pvc extension traps";
                    tailf:cli-optional-in-sequence;
                    leaf down {
                      tailf:info
                        "Enable SNMP atm pvc extended down trap";
                      tailf:cli-full-command;
                      type empty;
                    }
                    leaf up {
                      tailf:info
                        "Enable SNMP atm pvc extended up traps";
                      tailf:cli-full-command;
                      type empty;
                    }
                    leaf mibversion {
                      tailf:info
                        "Extension MIB version to be used";
                      tailf:cli-full-command;
                      type enumeration {
                        enum "1" {
                          tailf:info
                            "Use Extension mibversion 1";
                        }
                        enum "2" {
                          tailf:info
                            "Use Extension mibversion 2";
                        }
                      }
                    }
                    container oam {
                      tailf:info
                        "Enable SNMP atm pvc extended oam trap";
                      container failure {
                        tailf:info
                          "Enable SNMP atm pvc extended any oam failure trap";
                        leaf loopback {
                          tailf:info
                            "Enable SNMP atm pvc extended oam loopback failure trap";
                          tailf:cli-full-command;
                          type empty;
                        }
                      }
                    }
                  }
                  leaf interval {
                    tailf:info
                      "minimum period between successive traps";
                    tailf:cli-optional-in-sequence;
                    type uint16 {
                      tailf:info
                        "<1-3600>;;minimum period between successive traps (in seconds)";
                      range "1..3600";
                    }
                  }
                  leaf fail-interval {
                    tailf:info
                      "minimum period for storing the failed timestamp";
                    type uint16 {
                      tailf:info
                        "<0-3600>;;minimum period for storing the failed timestamp (in seconds)";
                      range "0..3600";
                    }
                  }
                }
                container subif {
                  tailf:info
                    "Enable SNMP atm subinterface traps";
                  tailf:cli-sequence-commands;
                  tailf:cli-delete-when-empty;
                  presence "true";
                  leaf interval {
                    tailf:info
                      "Interval duration in which to limit the number of traps sent";
                    tailf:cli-optional-in-sequence;
                    type uint16 {
                      tailf:info
                        "<0-3600>;;Duration of rate-limiting interval (0-3600 seconds)";
                      range "0..3600";
                    }
                  }
                  leaf count {
                    tailf:info
                      "Maximum number of traps sent per interval";
                    type uint16 {
                      tailf:info
                        "<1-1000>  Maximum traps per interval (1-1000)";
                      range "1..1000";
                    }
                  }
                }
              }
              leaf authenticate-fail {
                tailf:info
                  "Enable SNMP 802.11 Authentication Fail Trap";
                tailf:cli-full-command;
                type empty;
              }
              container auth-framework {
                tailf:cli-delete-when-empty;
                presence "true";
                leaf sec-violation {
                  type empty;
                }
              }
              leaf bfd {
                tailf:cli-full-command;
                type empty;
              }
              leaf bgp {
                tailf:info
                  "Enable BGP traps";
                tailf:cli-full-command;
                type empty;
              }
              container bridge {
                tailf:cli-delete-when-empty;
                presence "true";
                leaf newroot {
                  type empty;
                }
                leaf topologychange {
                  type empty;
                }
              }
              leaf bstun {
                tailf:info
                  "Enable SNMP BSTUN traps";
                tailf:cli-full-command;
                type empty;
              }
              container bulkstat {
                tailf:info
                  "Enable Data-Collection-MIB Collection notifications";
                tailf:cli-compact-syntax;
                tailf:cli-delete-when-empty;
                presence "true";
                leaf collection {
                  tailf:info
                    "Enable Data-Collection-MIB Collection notifications";
                  type empty;
                }
                leaf transfer {
                  tailf:info
                    "Enable Data-Collection-MIB Transfer notifications";
                  type empty;
                }
              }
              container call-home {
                tailf:info
                  "Enable CISCO-CALLHOME-MIB traps";
                tailf:cli-delete-when-empty;
                presence "true";
                leaf message-send-fail {
                  type empty;
                }
                leaf server-fail {
                  type empty;
                }
              }
              leaf c2900 {
                tailf:info
                  "Enable SNMP c2900 traps";
                tailf:cli-full-command;
                type empty;
              }
              container c6kxbar {
                tailf:info
                  "Enable SNMP CISCO-CAT6K-CROSSBAR-MIB traps";
                tailf:cli-delete-when-empty;
                presence "true";
                leaf intbus-crcexcd {
                  tailf:info
                    "Enable SNMP cc6kxbarIntBusCRCErrExcdNotif notification";
                  type empty;
                }
                leaf intbus-crcrcvrd {
                  tailf:info
                    "Enable SNMP cc6kxbarIntBusCRCErrRcvrdNotif notification";
                  type empty;
                }
                leaf swbus {
                  tailf:info
                    "Enable SNMP cc6kxbarSwBusStatusChangeNotif notification";
                  type empty;
                }
              }
              leaf casa {
                tailf:info
                  "Enable SNMP casa traps";
                tailf:cli-full-command;
                type empty;
              }
              leaf ccme {
                tailf:cli-full-command;
                type empty;
              }
              container cef {
                leaf resource-failure {
                  type empty;
                }
                leaf peer-state-change {
                  type empty;
                }
                leaf peer-fib-state-change {
                  type empty;
                }
                leaf inconsistency {
                  type empty;
                }
              }
              leaf cluster {
                tailf:info
                  "Enable Cluster traps";
                type empty;
              }
              leaf channel {
                tailf:info
                  "Enable SNMP channel traps";
                tailf:cli-full-command;
                type empty;
              }
              leaf chassis {
                tailf:info
                  "Enable SNMP chassis traps";
                type empty;
              }
              leaf cnpd {
                tailf:info
                  "Enable NBAR Protocol Discovery traps";
                tailf:cli-full-command;
                type empty;
              }
              leaf config {
                tailf:info
                  "Enable SNMP config traps";
                tailf:cli-full-command;
                type empty;
              }
              leaf copy-config {
                tailf:info
                  "Enable SNMP copy-config traps";
                tailf:cli-full-command;
                type empty;
              }
              leaf config-copy {
                tailf:info
                  "Enable SNMP config-copy traps";
                tailf:cli-full-command;
                type empty;
              }
              leaf config-ctid {
                tailf:cli-full-command;
                type empty;
              }
              container cpu {
                tailf:info
                  "Allow cpu related traps";
                tailf:cli-delete-when-empty;
                presence "true";
                leaf threshold {
                  tailf:info
                    "Allow CPU utilization threshold violation traps";
                  type empty;
                }
              }
              container csg {
                tailf:info
                  "Enable SNMP CSG traps";
                tailf:cli-delete-when-empty;
                presence "true";
                leaf agent {
                  tailf:info
                    "Enable SNMP Agent Server traps";
                  type empty;
                }
                leaf database {
                  tailf:info
                    "Enable SNMP CSG database traps";
                  type empty;
                }
                leaf quota-server {
                  tailf:info
                    "Enable SNMP Quota Server traps";
                  type empty;
                }
              }
              leaf dial {
                tailf:info
                  "Enable SNMP dial control traps";
                tailf:cli-full-command;
                type empty;
              }
              leaf director {
                tailf:info
                  "Enable SNMP Distributed Director traps";
                tailf:cli-full-command;
                type empty;
              }
              leaf dlsw {
                tailf:info
                  "Enable SNMP dlsw traps";
                tailf:cli-full-command;
                type empty;
              }
              leaf deauthenticate {
                tailf:info
                  "Enable SNMP 802.11 Deauthentication Trap";
                tailf:cli-full-command;
                type empty;
              }
              leaf disassociate {
                tailf:info
                  "Enable SNMP 802.11 Disassociation Trap";
                tailf:cli-full-command;
                type empty;
              }
              leaf dnis {
                tailf:info
                  "Enable SNMP DNIS traps";
                tailf:cli-full-command;
                type empty;
              }
              leaf dot11-qos {
                tailf:info
                  "Enable SNMP 802.11 QoS Change Trap";
                tailf:cli-full-command;
                type empty;
              }
              container dot1x {
                leaf auth-fail-vlan {
                  type empty;
                }
                leaf guest-vlan {
                  type empty;
                }
                leaf no-auth-fail-vlan {
                  type empty;
                }
                leaf no-guest-vlan {
                  type empty;
                }
              }
              leaf ds0-busyout {
                tailf:info
                  "Enable ds0-busyout traps";
                tailf:cli-full-command;
                type empty;
              }
              leaf ds1 {
                tailf:info
                  "Enable SNMP DS1 traps";
                tailf:cli-full-command;
                type empty;
              }
              leaf ds1-loopback {
                tailf:info
                  "Enable ds1-loopback traps";
                tailf:cli-full-command;
                type empty;
              }
              leaf ds3 {
                tailf:info
                  "Enable SNMP DS3 traps";
                tailf:cli-full-command;
                type empty;
              }
              container dsp {
                tailf:info
                  "Enable SNMP dsp traps";
                tailf:cli-delete-when-empty;
                presence "true";
                leaf card-status {
                  tailf:info
                    "Enable SNMP card status of dsp traps";
                  type empty;
                }
                leaf oper-state {
                  type empty;
                }
              }
              leaf eigrp {
                tailf:info
                  "Enable SNMP EIGRP traps";
                tailf:cli-full-command;
                type empty;
              }
              container energywise {
                tailf:cli-delete-when-empty;
                presence "true";
                leaf event-occured {
                  type empty;
                }
                leaf level-change {
                  type empty;
                }
                leaf neighbor-added {
                  type empty;
                }
                leaf neighbor-deleted {
                  type empty;
                }
              }
              leaf entity {
                tailf:info
                  "Enable SNMP entity traps";
                tailf:cli-full-command;
                type empty;
              }
              container entity-diag {
                tailf:info
                  "Enable SNMP CISCO-ENTITY-DIAG-MIB traps";
                tailf:cli-delete-when-empty;
                presence "true";
                leaf boot-up-fail {
                  tailf:info
                    "Enable SNMP ceDiagBootUpFailedNotif traps";
                  type empty;
                }
                leaf hm-test-recover {
                  tailf:info
                    "Enable SNMP ceDiagHMTestRecoverNotif traps";
                  type empty;
                }
                leaf hm-thresh-reached {
                  tailf:info
                    "Enable SNMP ceDiagHMThresholdReachedNotif traps";
                  type empty;
                }
                leaf scheduled-test-fail {
                  tailf:info
                    "Enable SNMP ceDiagScheduledTestFailedNotif traps";
                  type empty;
                }
              }
              container envmon {
                tailf:info
                  "Enable SNMP environmental monitor traps";
                tailf:cli-delete-when-empty;
                presence "true";
                leaf fan {
                  type empty;
                }
                leaf shutdown {
                  type empty;
                }
                leaf supply {
                  type empty;
                }
                leaf temperature {
                  type empty;
                }
                leaf status {
                  type empty;
                }
              }
              container errdisable {
                tailf:info
                  "Enable SNMP errdisable notifications";
                tailf:cli-delete-when-empty;
                presence "true";
                leaf notification-rate {
                  tailf:info
                    "Number of notifications per minute";
                  type uint16 {
                    tailf:info
                      "<0-10000>;;Number of notificatios per minute";
                    range "0..10000";
                  }
                }
              }
              leaf ether-oam {
                tailf:cli-full-command;
                type empty;
              }
              container ethernet {
                container cfm {
                  leaf alarm {
                    tailf:info
                      "Enable SNMP Ethernet CFM fault alarm trap";
                    type empty;
                  }
                  container cc {
                    tailf:cli-delete-when-empty;
                    presence "true";
                    leaf config {
                      type empty;
                    }
                    leaf cross-connect {
                      type empty;
                    }
                    leaf loop {
                      type empty;
                    }
                    leaf mep-down {
                      type empty;
                    }
                    leaf mep-up {
                      type empty;
                    }
                  }
                  container crosscheck {
                    tailf:cli-delete-when-empty;
                    presence "true";
                    leaf mep-missing {
                      type empty;
                    }
                    leaf mep-unknown {
                      type empty;
                    }
                    leaf service-up {
                      type empty;
                    }
                  }
                }
                container evc {
                  tailf:info
                    "Enable SNMP Ethernet EVC traps";
                  tailf:cli-delete-when-empty;
                  presence "true";
                  leaf create {
                    tailf:info
                      "Enable SNMP Ethernet EVC create traps";
                    type empty;
                  }
                  leaf delete {
                    tailf:info
                      "Enable SNMP Ethernet EVC delete traps";
                    type empty;
                  }
                  leaf status {
                    tailf:info
                      "Enable SNMP Ethernet EVC status traps";
                    type empty;
                  }
                }
              }
              leaf event-manager {
                tailf:info
                  "Enable SNMP Embedded Event Manager traps";
                tailf:cli-full-command;
                type empty;
              }
              container firewall {
                tailf:cli-delete-when-empty;
                presence "true";
                leaf serverstatus {
                  type empty;
                }
              }
              container flash {
                tailf:info
                  "Enable SNMP FLASH notifications";
                tailf:cli-delete-when-empty;
                presence "true";
                leaf insertion {
                  tailf:info
                    "Enable SNMP Flash Insertion notifications";
                  type empty;
                }
                leaf removal {
                  tailf:info
                    "Enable SNMP Flash Removal notifications";
                  type empty;
                }
              }
              leaf flowmon {
                tailf:info
                  "Enabel SNMP flowmon notifications";
                type empty;
              }
              container flex-links {
                tailf:info
                  "Enable SNMP FLEX Links traps";
                tailf:cli-delete-when-empty;
                presence "true";
                leaf status {
                  tailf:info
                    "Enable SNMP FLEX Links status change traps";
                  type empty;
                }
              }
              container frame-relay {
                tailf:info
                  "Enable SNMP frame-relay traps";
                tailf:cli-delete-when-empty;
                presence "true";
                container multilink {
                  tailf:info
                    "Enable MFR traps";
                  leaf bundle-mismatch {
                    tailf:info
                      "Enable MFR trap for inconsistent bundle event";
                    type empty;
                  }
                }
                container subif {
                  tailf:info
                    "Enable SNMP frame-relay subinterface traps";
                  tailf:cli-delete-when-empty;
                  presence "true";
                }
              }
              leaf fru-ctrl {
                tailf:info
                  "Enable SNMP entity FRU control traps";
                tailf:cli-full-command;
                type empty;
              }
              leaf gatekeeper {
                tailf:info
                  "Enable SNMP gatekeeper traps";
                tailf:cli-full-command;
                type empty;
              }
              leaf hsrp {
                tailf:info
                  "Enable SNMP HSRP traps";
                tailf:cli-full-command;
                type empty;
              }
              leaf icsudsu {
                tailf:info
                  "Enable SNMP ICSUDSU traps";
                tailf:cli-full-command;
                type empty;
              }
              leaf ima {
                tailf:info
                  "Enable SNMP ATM IMA traps";
                tailf:cli-full-command;
                type empty;
              }
              leaf ipmobile {
                tailf:info
                  "Enable SNMP ipmobile traps";
                tailf:cli-full-command;
                type empty;
              }
              leaf ipmulticast {
                tailf:info
                  "Enable SNMP ipmulticast traps";
                tailf:cli-full-command;
                type empty;
              }
              container ipsec {
                tailf:info
                  "Enable IPsec traps";
                container cryptomap {
                  leaf add {
                    tailf:info
                      "Enable IPsec Cryptomap add trap";
                    tailf:cli-full-command;
                    type empty;
                  }
                  leaf attach {
                    tailf:info
                      "Enable IPsec Cryptomap Attach trap";
                    tailf:cli-full-command;
                    type empty;
                  }
                  leaf delete {
                    tailf:info
                      "Enable IPsec Cryptomap delete trap";
                    tailf:cli-full-command;
                    type empty;
                  }
                  leaf detach {
                    tailf:info
                      "Enable IPsec Cryptomap Detach trap";
                    tailf:cli-full-command;
                    type empty;
                  }
                }
                container tunnel {
                  tailf:info
                    "Enable IPsec Tunnel traps";
                  leaf start {
                    tailf:info
                      "Enable IPsec Tunnel Start trap";
                    tailf:cli-full-command;
                    type empty;
                  }
                  leaf stop {
                    tailf:info
                      "Enable IPsec Tunnel Stop trap";
                    tailf:cli-full-command;
                    type empty;
                  }
                }
                leaf too-many-sas {
                  tailf:info
                    "Enable IPsec Tunnel Start trap";
                  type empty;
                }
              }
              container isakmp {
                tailf:info
                  "Enable ISAKMP traps traps";
                container policy {
                  tailf:info
                    "Enable ISAKMP traps";
                  leaf add {
                    tailf:info
                      "Enable ISAKMP Policy add trap";
                    type empty;
                  }
                  leaf delete {
                    tailf:info
                      "Enable ISAKMP Policy delete trap";
                    type empty;
                  }
                }
                container tunnel {
                  tailf:info
                    "Enable ISAKMP Tunnel traps";
                  leaf start {
                    tailf:info
                      "Enable ISAKMP Tunnel start trap";
                    type empty;
                  }
                  leaf stop {
                    tailf:info
                      "Enable ISAKMP Tunnel stop trap";
                    type empty;
                  }
                }
              }
              container isdn {
                tailf:info
                  "Enable SNMP isdn traps";
                tailf:cli-delete-when-empty;
                presence "true";
                leaf call-information {
                  tailf:info
                    "Enable SNMP isdn call information traps";
                  type empty;
                }
                leaf chan-not-avail {
                  tailf:info
                    "Enable SNMP isdn channel not avail traps";
                  type empty;
                }
                leaf ietf {
                  tailf:info
                    "Enable SNMP isdn ietf traps";
                  type empty;
                }
                leaf layer2 {
                  tailf:info
                    "Enable SNMP isdn layer2 transition traps";
                  type empty;
                }
              }
              leaf ipsla {
                tailf:info
                  "Enable IPSLA traps traps";
                tailf:cli-full-command;
                type empty;
              }
              leaf isis {
                tailf:info
                  "Enable ISIS traps traps";
                tailf:cli-full-command;
                type empty;
              }
              container l2tc {
                tailf:info
                  "Enable SNMP L2 Tunnel Config traps";
                tailf:cli-delete-when-empty;
                presence "true";
                tailf:cli-compact-syntax;
                leaf sys-threshold {
                  tailf:info
                    "Enable SNMP L2TC System threshold traps";
                  type empty;
                }
                leaf threshold {
                  tailf:info
                    "Enable SNMP L2 Tunnel Config threshold traps";
                  type empty;
                }
              }
              container l2tun {
                tailf:info
                  "Enable SNMP L2 tunnel protocol traps";
                leaf session {
                  tailf:info
                    "Enable SNMP l2tun session traps";
                  tailf:cli-full-command;
                  type empty;
                }
                container pseudowire {
                  leaf status {
                    type empty;
                  }
                }
              }
              leaf license {
                tailf:cli-full-command;
                type empty;
              }
              container mac-notification {
                tailf:cli-delete-when-empty;
                presence "true";
                container change {
                  tailf:cli-delete-when-empty;
                  presence "true";
                  leaf move {
                    type empty;
                  }
                  leaf threshold {
                    type empty;
                  }
                }
              }
              container mac-notification2 {
                tailf:alt-name "MAC-Notification";
                tailf:cli-delete-when-empty;
                presence "true";
                leaf move {
                  type empty;
                }
                leaf threshold {
                  type empty;
                }
              }
              container memory {
                tailf:info
                  "Enable SNMP Memory traps";
                leaf bufferpeak {
                  tailf:info
                    "Enable SNMP Memory Bufferpeak traps";
                  tailf:cli-full-command;
                  type empty;
                }
              }
              leaf module {
                tailf:info
                  "Enable SNMP module traps";
                type empty;
              }
              container mpls {
                tailf:info
                  "Enable SNMP MPLS traps";
                tailf:cli-delete-when-empty;
                presence "true";
                container traffic-eng {
                  tailf:cli-delete-when-empty;
                  presence "true";
                }
                container fast-reroute {
                  tailf:cli-delete-when-empty;
                  presence "true";
                  leaf protected {
                    type empty;
                  }
                }
                container rfc {
                  tailf:cli-delete-when-empty;
                  presence "true";
                  leaf ldp {
                    type empty;
                  }
                }
                container ldp {
                  tailf:info
                    "SNMP MPLS label distribution protocol traps";
                  tailf:cli-delete-when-empty;
                  presence "true";
                  leaf pv-limit {
                    tailf:info
                      "Enable MPLS LDP path vector limit mismatch traps";
                    type empty;
                  }
                  leaf session-down {
                    tailf:info
                      "Enable MPLS LDP session down traps";
                    type empty;
                  }
                  leaf session-up {
                    tailf:info
                      "Enable MPLS LDP session up traps";
                    type empty;
                  }
                  leaf threshold {
                    tailf:info
                      "Enable MPLS LDP threshold exceeded traps";
                    type empty;
                  }
                }
                leaf vpn {
                  type empty;
                }
              }
              leaf msdp {
                tailf:info
                  "Enable SNMP MSDP traps";
                tailf:cli-full-command;
                type empty;
              }
              leaf mvpn {
                tailf:info
                  "Enable Multicast Virtual Private Networks traps";
                tailf:cli-full-command;
                type empty;
              }
              container nhrp {
                tailf:cli-delete-when-empty;
                presence "true";
                container nhs {
                  presence "true";
                }
                container nhc {
                  presence "true";
                }
                container nhp {
                  presence "true";
                }
                container quota-exceeded {
                  presence "true";
                }
              }
              container ospf {
                tailf:info
                  "Enable OSPF traps";
                container state-change {
                  tailf:info
                    "State change traps";
                  tailf:cli-delete-when-empty;
                  presence "true";
                  leaf if-state-change {
                    tailf:info
                      "Non-virtual interface state changes";
                    type empty;
                  }
                  leaf neighbor-state-change {
                    tailf:info
                      "Non-virtual neighbor state changes";
                    type empty;
                  }
                  leaf virtif-state-change {
                    tailf:info
                      "Virtual interface state changes";
                    type empty;
                  }
                  leaf virtneighbor-state-change {
                    tailf:info
                      "Non-virtual neighbor state changes";
                    type empty;
                  }
                }
                container errors {
                  tailf:info
                    "Error traps";
                  tailf:cli-delete-when-empty;
                  presence "true";
                }
                container retransmit {
                  tailf:info
                    "Packet retransmit traps";
                  tailf:cli-delete-when-empty;
                  presence "true";
                  leaf packets {
                    tailf:info
                      "Packet retransmission on non-virtual interfaces";
                    type empty;
                  }
                  leaf virt-packets {
                    tailf:info
                      "Packet retransmission on virtual interfaces";
                    type empty;
                  }
                }
                container lsa {
                  tailf:info
                    "Lsa related traps";
                  tailf:cli-delete-when-empty;
                  presence "true";
                  leaf lsa-maxage {
                    tailf:info
                      "Lsa aged to maxage";
                    type empty;
                  }
                  leaf lsa-originate {
                    tailf:info
                      "New lsa originated";
                    type empty;
                  }
                }
                container cisco-specific {
                  tailf:info
                    "Cisco specific traps";
                  tailf:cli-delete-when-empty;
                  presence "true";
                  container state-change {
                    tailf:info
                      "State change traps";
                    tailf:cli-delete-when-empty;
                    presence "true";
                    leaf nssa-trans-change {
                      tailf:info
                        "Nssa translator state changes";
                      type empty;
                    }
                    container shamlink {
                      tailf:info
                        "Sham link state change traps";
                      tailf:cli-delete-when-empty;
                      presence "true";
                      leaf interface {
                        tailf:info
                          "Sham link interface state changes";
                        type empty;
                      }
                      leaf interface-old {
                        tailf:info
                          "Sham link interface state changes (deprecated)";
                        type empty;
                      }
                      leaf neighbor {
                        tailf:info
                          "Sham link neighbor state changes";
                        type empty;
                      }
                    }
                  }
                  container errors {
                    tailf:info
                      "Error traps";
                    tailf:cli-delete-when-empty;
                    presence "true";
                  }
                  container errdisable {
                    tailf:info
                      "Enable SNMP errdisable notifications";
                    tailf:cli-delete-when-empty;
                    presence "true";
                    leaf notification-rate {
                      tailf:info
                        "Number of notifications per minute";
                      type uint16 {
                        tailf:info
                          "<0-10000>;;Number of notificatios per minute";
                        range "0..10000";
                      }
                    }
                  }
                  container retransmit {
                    tailf:info
                      "Packet retransmit traps";
                    tailf:cli-delete-when-empty;
                    presence "true";
                  }
                  container lsa {
                    tailf:info
                      "Lsa related traps";
                    tailf:cli-delete-when-empty;
                    presence "true";
                    leaf lsa-maxage {
                      tailf:info
                        "Lsa aged to maxage";
                      type empty;
                    }
                    leaf lsa-originate {
                      tailf:info
                        "New lsa originated";
                      type empty;
                    }
                  }
                }
              }
              container pim {
                tailf:info
                  "Enable SNMP PIM traps";
                tailf:cli-delete-when-empty;
                presence "true";
                leaf invalid-pim-message {
                  tailf:info
                    "Enable invalid pim message trap";
                  type empty;
                }
                leaf neighbor-change {
                  tailf:info
                    "Enable neighbor change trap";
                  type empty;
                }
                leaf rp-mapping-change {
                  tailf:info
                    "Enable rp mapping change trap";
                  type empty;
                }
              }
              container port-security {
                tailf:info
                  "Enable SNMP port security traps";
                tailf:cli-delete-when-empty;
                presence "true";
                leaf trap-rate {
                  tailf:info
                    "Number of traps per second";
                  type uint16 {
                    tailf:info
                      "<0-1000>;;Number of traps per second";
                    range "0..1000";
                  }
                }
              }
              container power-ethernet {
                tailf:info
                  "Enable SNMP power ethernet traps";
                leaf group {
                  tailf:info
                    "Enable SNMP inline power group based traps";
                  type string {
                    tailf:info
                      "WORD;;The group number or list";
                  }
                }
                leaf police {
                  tailf:info
                    "Enable Policing Trap";
                  type empty;
                }
              }
              leaf pppoe {
                tailf:info
                  "Enable SNMP pppoe traps";
                tailf:cli-full-command;
                type empty;
              }
              container pw {
                tailf:cli-delete-when-empty;
                presence "true";
                leaf vc {
                  type empty;
                }
              }
              leaf rep {
                tailf:cli-full-command;
                type empty;
              }
              leaf resource-policy {
                tailf:cli-full-command;
                type empty;
              }
              leaf rf {
                tailf:info
                  "Enable all SNMP traps defined in CISCO-RF-MIB";
                tailf:cli-full-command;
                type empty;
              }
              leaf rogue-ap {
                tailf:info
                  "Enable SNMP 802.11 Rogue AP Trap";
                tailf:cli-full-command;
                type empty;
              }
              leaf rsvp {
                tailf:info
                  "Enable RSVP flow change traps";
                tailf:cli-full-command;
                type empty;
              }
              leaf rtr {
                tailf:info
                  "Enable SNMP Response Time Reporter traps";
                tailf:cli-full-command;
                type empty;
              }
              container slb {
                tailf:info
                  "Enable SNMP SLB traps";
                tailf:cli-delete-when-empty;
                presence "true";
                leaf csrp {
                  tailf:info
                    "Enable SNMP SLB Fault Tolerance Replication Protocol traps";
                  type empty;
                }
                leaf real {
                  tailf:info
                    "Enable SNMP SLB Real Server traps";
                  type empty;
                }
                leaf virtual {
                  tailf:info
                    "Enable SNMP SLB Virtual Server traps";
                  type empty;
                }
              }
              container snmp {
                tailf:info
                  "Enable SNMP traps";
                tailf:cli-compact-syntax;
                leaf authentication {
                  tailf:info
                    "Enable authentication trap";
                  type empty;
                }
                leaf coldstart {
                  tailf:info
                    "Enable coldStart trap";
                  type empty;
                }
                leaf linkdown {
                  tailf:info
                    "Enable linkDown trap";
                  type empty;
                }
                leaf linkup {
                  tailf:info
                    "Enable linkUp trap";
                  type empty;
                }
                leaf warmstart {
                  tailf:info
                    "Enable warmStart trap";
                  type empty;
                }
              }
              leaf sonet {
                tailf:info
                  "Enable SNMP SONET traps";
                type empty;
              }
              leaf srst {
                tailf:cli-full-command;
                type empty;
              }
              leaf srp {
                tailf:info
                  "Enable SRP protocol traps";
                tailf:cli-full-command;
                type empty;
              }
              container stackwise {
                tailf:info
                  "Enable SNMP stackwise traps";
                tailf:cli-delete-when-empty;
                presence "true";
                leaf GLS {
                  tailf:info
                    "Enable STACKWISE stack power GLS trap";
                  type empty;
                }
                leaf ILS {
                  tailf:info
                    "Enable STACKWISE stack power ILS trap";
                  type empty;
                }
                leaf SRLS {
                  tailf:info
                    "Enable STACKWISE stack power SRLS trap";
                  type empty;
                }
                leaf insufficient-power {
                  tailf:info
                    "Enable STACKWISE stack power unbalanced power supplies trap";
                  type empty;
                }
                leaf invalid-input-current {
                  tailf:info
                    "Enable STACKWISE stack power invalid input current trap";
                  type empty;
                }
                leaf invalid-output-current {
                  tailf:info
                    "Enable STACKWISE stack power invalid output current trap";
                  type empty;
                }
                leaf member-removed {
                  tailf:info
                    "Enable STACKWISE stack member removed trap";
                  type empty;
                }
                leaf member-upgrade-notification {
                  tailf:info
                    "Enable STACKWISE member to be reloaded for upgrade trap";
                  type empty;
                }
                leaf new-master {
                  tailf:info
                    "Enable STACKWISE new master trap";
                  type empty;
                }
                leaf new-member {
                  tailf:info
                    "Enable STACKWISE stack new member trap";
                  type empty;
                }
                leaf port-change {
                  tailf:info
                    "Enable STACKWISE port change trap";
                  type empty;
                }
                leaf power-budget-warning {
                  tailf:info
                    "Enable STACKWISE stack power budget warning trap";
                  type empty;
                }
                leaf power-invalid-topology {
                  tailf:info
                    "Enable STACKWISE stack power invalid topology trap";
                  type empty;
                }
                leaf power-link-status-changed {
                  tailf:info
                    "Enable STACKWISE stack power link status changed trap";
                  type empty;
                }
                leaf power-oper-status-changed {
                  tailf:info
                    "Enable STACKWISE stack power port oper status changed trap";
                  type empty;
                }
                leaf power-priority-conflict {
                  tailf:info
                    "Enable STACKWISE stack power priority conflict trap";
                  type empty;
                }
                leaf power-version-mismatch {
                  tailf:info
                    "Enable STACKWISE stack power version mismatch discovered trap";
                  type empty;
                }
                leaf ring-redundant {
                  tailf:info
                    "Enable STACKWISE stack ring redundant trap";
                  type empty;
                }
                leaf stack-mismatch {
                  tailf:info
                    "Enable STACKWISE stack mismatch trap";
                  type empty;
                }
                leaf unbalanced-power-supplies {
                  tailf:info
                    "Enable STACKWISE stack power unbalanced power supplies trap";
                  type empty;
                }
                leaf under-budget {
                  tailf:info
                    "Enable STACKWISE stack power under budget trap";
                  type empty;
                }
                leaf under-voltage {
                  tailf:info
                    "Enable STACKWISE stack power under voltage trap";
                  type empty;
                }
              }
              container stpx {
                tailf:cli-delete-when-empty;
                presence "true";
                leaf inconsistency {
                  type empty;
                }
                leaf root-inconsistency {
                  type empty;
                }
                leaf loop-inconsistency {
                  type empty;
                }
              }
              leaf stun {
                tailf:info
                  "Enable SNMP STUN traps";
                tailf:cli-full-command;
                type empty;
              }
              leaf switch-over {
                tailf:info
                  "Enable SNMP 802.11 Standby Switch-over Trap";
                tailf:cli-full-command;
                type empty;
              }
              leaf syslog {
                tailf:info
                  "Enable SNMP syslog traps";
                tailf:cli-full-command;
                type empty;
              }
              container transceiver {
                leaf all {
                  type empty;
                }
              }
              leaf tty {
                tailf:info
                  "Enable TCP connection traps";
                tailf:cli-full-command;
                type empty;
              }
              container udld {
                tailf:info
                  "Enable SNMP CISCO-UDLDP-MIB traps";
                tailf:cli-compact-syntax;
                tailf:cli-delete-when-empty;
                presence "true";
                leaf link-fail-rpt {
                  tailf:info
                    "Enable SNMP cudldpFastHelloLinkFailRptNotification traps";
                  type empty;
                }
                leaf status-change {
                  tailf:info
                    "Enable SNMP cudldpFastHelloStatusChangeNotification traps";
                  type empty;
                }
              }
              leaf vlancreate {
                tailf:cli-full-command;
                type empty;
              }
              leaf vlandelete {
                tailf:cli-full-command;
                type empty;
              }
              leaf vlan-mac-limit {
                tailf:info
                  "Enable SNMP L2 Control VLAN MAC Limit notifications";
                type empty;
              }
              leaf vlan-membership {
                tailf:cli-full-command;
                type empty;
              }
              leaf voice {
                tailf:info
                  "Enable SNMP voice traps";
                tailf:cli-full-command;
                type empty;
              }
              container vrfmib {
                leaf vrf-up {
                  type empty;
                }
                leaf vrf-down {
                  type empty;
                }
                leaf vnet-trunk-up {
                  type empty;
                }
                leaf vnet-trunk-down {
                  type empty;
                }
              }
              leaf vrrp {
                tailf:info
                  "Enable SNMP vrrp traps";
                tailf:cli-full-command;
                type empty;
              }
              leaf vsimaster {
                tailf:info
                  "Allow SNMP vsimaster traps";
                tailf:cli-full-command;
                type empty;
              }
              container vstack {
                tailf:info
                  "Enable SNMP Smart Install traps";
                tailf:cli-delete-when-empty;
                presence "true";
                tailf:cli-compact-syntax;
                leaf addition {
                  tailf:info
                    "Enable client added trap";
                  type empty;
                }
                leaf failure {
                  tailf:info
                    "Enable file upload/download failure trap";
                  type empty;
                }
                leaf lost {
                  tailf:info
                    "Enable client lost trap";
                  type empty;
                }
                leaf operation {
                  tailf:info
                    "Enable operation mode change trap";
                  type empty;
                }
              }
              leaf vtp {
                tailf:cli-full-command;
                type empty;
              }
              leaf wlan-wep {
                tailf:info
                  "Enable SNMP 802.11 WLAN WEP Trap";
                tailf:cli-full-command;
                type empty;
              }
              leaf xgcp {
                tailf:info
                  "Enable XGCP protocol traps";
                tailf:cli-full-command;
                type empty;
              }
            }
          }
        }
      }
      container engineID {
        tailf:info
          "Configure a local or remote SNMPv3 engineID";
        leaf local {
          tailf:info
            "engineID of the local agent";
          type string {
            tailf:info
              "WORD;;engine ID octet string";
            length "1..24";
          }
        }
        container remote {
          tailf:info
            "engineID of the remote agent";
        }
      }
      list group {
        tailf:info
          "Define a User Security Model group";
        tailf:cli-suppress-mode;
        tailf:cli-delete-when-empty;
        tailf:cli-compact-syntax;
        tailf:cli-sequence-commands;
        key "id";
        leaf id {
          type string {
            tailf:info
              "WORD;;Name of the group";
          }
        }
        choice security-model {
          container v1 {
            tailf:info
              "group using the v1 security model";
          }
          container v2c {
            tailf:info
              "group using the v2c security model";
          }
          container v3 {
            tailf:info
              "group using the User Security Model (SNMPv3)";
            tailf:cli-compact-syntax;
            tailf:cli-sequence-commands {
              tailf:cli-reset-siblings;
            }
            leaf security-level {
              tailf:cli-drop-node-name;
              type enumeration {
                enum "auth" {
                  tailf:info
                    "group using the authNoPriv Security Level";
                }
                enum "noauth" {
                  tailf:info
                    "group using the noAuthNoPriv Security Level";
                }
                enum "priv" {
                  tailf:info
                    "group using SNMPv3 authPriv security level";
                }
              }
            }
            leaf context {
              tailf:cli-optional-in-sequence;
              tailf:info
                "specify a context to associate these views for the group";
              type string {
                tailf:info
                  "WORD;;context name";
              }
            }
            leaf match {
              tailf:cli-optional-in-sequence;
              tailf:info
                "context name match criteria";
              type enumeration {
                enum "exact" {
                  tailf:info
                    "match the exact context";
                }
                enum "prefix" {
                  tailf:info
                    "only match the context prefix";
                }
              }
            }
            leaf read {
              tailf:cli-optional-in-sequence;
              tailf:info
                "specify a read view for the group";
              type string {
                tailf:info
                  "WORD;;read view name";
              }
            }
            leaf write {
              tailf:cli-optional-in-sequence;
              tailf:info
                "specify a write view for the group";
              type string {
                tailf:info
                  "WORD;;write view name";
              }
            }
            leaf notify {
              tailf:cli-optional-in-sequence;
              tailf:info
                "specify a notify view for the group";
              type string {
                tailf:info
                  "WORD;;notify view name";
              }
            }
            leaf access {
              tailf:info
                "specify an access-list associated with this group";
              type union {
                type uint8 {
                  tailf:info
                    "<1-99>;;Std IP accesslist allowing access with this group";
                  range "1..99";
                }
                type string {
                  tailf:info
                    "WORD;;Access-list name";
                }
              }
            }
          }
        }
      }
      list host {
        tailf:info
          "Specify hosts to receive SNMP notifications";
        tailf:cli-suppress-mode;
        tailf:cli-delete-when-empty;
        tailf:cli-sequence-commands;
        tailf:cli-compact-syntax;
        tailf:cli-incomplete-command;
        key "ip-address";
        leaf ip-address {
          type host-type {
            tailf:info
              "WORD;;Hostname or IP/IPv6 address of SNMP notification host";
          }
        }
        leaf vrf {
          tailf:info
            "VPN Routing instance for this host";
          tailf:cli-optional-in-sequence;
          tailf:cli-incomplete-command;
          tailf:cli-diff-dependency "/ios:ip/vrf" {
            tailf:xpath-root 3;
          }
          tailf:cli-diff-dependency "/ios:vrf/definition" {
            tailf:xpath-root 3;
          }
          type string;
        }
        choice informs-traps-choice {
          leaf informs {
            tailf:info
              "Send Inform messages to this host";
            tailf:cli-optional-in-sequence;
            tailf:cli-incomplete-command;
            type empty;
          }
          leaf traps {
            tailf:info
              "Send Trap messages to this host";
            tailf:cli-optional-in-sequence;
            tailf:cli-incomplete-command;
            type empty;
          }
          default "traps";
        }
        container version {
          tailf:info
            "SNMP version to use for notification messages";
          tailf:cli-optional-in-sequence;
          tailf:cli-flatten-container;
          tailf:cli-incomplete-command;
          leaf version {
            tailf:cli-drop-node-name;
            type enumeration {
              enum "1" {
                tailf:info
                  "Use SNMPv1";
              }
              enum "2c" {
                tailf:info
                  "Use SNMPv2c";
              }
              enum "3" {
                tailf:info
                  "Use SNMPv3";
              }
            }
          }
          leaf security-level {
            tailf:cli-drop-node-name;
            when "../version = '3'" {
              tailf:xpath-root 3;
            }
            type enumeration {
              enum "auth" {
                tailf:info
                  "Use the SNMPv3 authNoPriv Security Level";
              }
              enum "noauth" {
                tailf:info
                  "Use the SNMPv3 noAuthNoPriv Security Level";
              }
              enum "priv" {
                tailf:info
                  "Use the SNMPv3 authPriv Security Level";
              }
            }
          }
        }
        list community-string {
          tailf:cli-drop-node-name;
          tailf:cli-suppress-mode;
          tailf:cli-compact-syntax;
          tailf:cli-delete-when-empty;
          key "name";
          leaf name {
            type string {
              tailf:info
                "WORD;;SNMPv1/v2c community string or SNMPv3 user name";
            }
          }
          leaf aaa_server {
            tailf:info
              "Allow SNMP AAA traps";
            type empty;
          }
          leaf alarms {
            tailf:info
              "Allow SNMP alarms traps";
            type empty;
          }
          leaf atm {
            tailf:info
              "Allow SNMP atm traps";
            type empty;
          }
          leaf bfd {
            tailf:info
              "Allow SNMP BFD traps";
            type empty;
          }
          leaf bgp {
            tailf:info
              "Allow BGP state change traps";
            type empty;
          }
          leaf bstun {
            tailf:info
              "Allow bstun event traps";
            type empty;
          }
          leaf bulkstat {
            tailf:info
              "Allow Data-Collection-MIB traps";
            type empty;
          }
          leaf call-home {
            tailf:info
              "Allow SNMP CISCO-CALLHOME-MIB traps";
            type empty;
          }
          leaf casa {
            tailf:info
              "Allow casa event traps";
            type empty;
          }
          leaf cef {
            tailf:info
              "Allows cef traps";
            type empty;
          }
          leaf cnpd {
            tailf:info
              "Allow NBAR Protocol Discovery traps";
            type empty;
          }
          leaf config {
            tailf:info
              "Allow SNMP config traps";
            type empty;
          }
          leaf config-copy {
            tailf:info
              "Allow SNMP config-copy traps";
            type empty;
          }
          leaf config-ctid {
            tailf:info
              "Allow SNMP config-ctid traps";
            type empty;
          }
          leaf cpu {
            tailf:info
              "Allow cpu related traps";
            type empty;
          }
          leaf dhcp {
            tailf:info
              "Allow dhcp traps";
            type empty;
          }
          leaf dlsw {
            tailf:info
              "Allow dlsw traps";
            type empty;
          }
          leaf ds1 {
            tailf:info
              "Allow SNMP ds1 traps";
            type empty;
          }
          leaf dsp {
            tailf:info
              "Allow SNMP DSP traps";
            type empty;
          }
          leaf dspu {
            tailf:info
              "Allow dspu event traps";
            type empty;
          }
          leaf eigrp {
            tailf:info
              "Allow SNMP EIGRP traps";
            type empty;
          }
          leaf entity {
            tailf:info
              "Allow SNMP entity traps";
            type empty;
          }
          leaf entity-diag {
            tailf:info
              "Allow SNMP CISCO-ENTITY-DIAG-MIB traps";
            type empty;
          }
          leaf entity-qfp {
            tailf:info
              "Allow SNMP CISCO-ENTITY-QFP-MIB traps";
            type empty;
          }
          leaf entity-state {
            tailf:info
              "Allow ENTITY-STATE-MIB traps";
            type empty;
          }
          leaf ethernet-cfm {
            tailf:info
              "Allow SNMP Ethernet CFM traps";
            type empty;
          }
          leaf evc {
            tailf:info
              "Allow SNMP EVC traps";
            type empty;
          }
          leaf event-manager {
            tailf:info
              "Allow SNMP Embedded Event Manager traps";
            type empty;
          }
          leaf firewall {
            tailf:info
              "Allow SNMP Firewall traps";
            type empty;
          }
          leaf flash {
            tailf:info
              "Allow SNMP FLASH traps";
            type empty;
          }
          leaf flowmon {
            tailf:info
              "Allow SNMP flow monitor notifications";
            type empty;
          }
          leaf frame-relay {
            tailf:info
              "Allow SNMP frame-relay traps";
            type empty;
          }
          leaf fru-ctrl {
            tailf:info
              "Allow entity FRU control traps";
            type empty;
          }
          leaf gdoi {
            tailf:info
              "Allows gdoi traps";
            type empty;
          }
          leaf hsrp {
            tailf:info
              "Allow SNMP HSRP traps";
            type empty;
          }
          leaf iplocalpool {
            tailf:info
              "Allow SNMP IP Local Pool traps";
            type empty;
          }
          leaf ipmulticast {
            tailf:info
              "Allow SNMP ipmulticast traps";
            type empty;
          }
          leaf ipsec {
            tailf:info
              "Allow SNMP IPsec traps";
            type empty;
          }
          leaf ipsla {
            tailf:info
              "Allow SNMP Host IP SLA traps";
            type empty;
          }
          leaf isakmp {
            tailf:info
              "Allow SNMP ISAKMP traps";
            type empty;
          }
          leaf isg-mib {
            tailf:info
              "Allow SNMP isgmib traps";
            type empty;
          }
          leaf isis {
            tailf:info
              "Allow IS-IS traps";
            type empty;
          }
          leaf l2tun-pseudowire-status {
            tailf:info
              "Allow SNMP L2 pseudowire status traps";
            type empty;
          }
          leaf l2tun-session {
            tailf:info
              "Allow SNMP L2 session traps";
            type empty;
          }
          leaf license {
            tailf:info
              "Allow license traps";
            type empty;
          }
          leaf memory {
            tailf:info
              "Allow SNMP Mempool traps";
            type empty;
          }
          leaf mpls-fast-reroute {
            tailf:info
              "Allow SNMP MPLS traffic engineering fast reroute traps";
            type empty;
          }
          leaf mpls-ldp {
            tailf:info
              "Allow SNMP MPLS label distribution protocol traps";
            type empty;
          }
          leaf mpls-traffic-eng {
            tailf:info
              "Allow SNMP MPLS traffic engineering traps";
            type empty;
          }
          leaf mpls-vpn {
            tailf:info
              "Allow SNMP MPLS Virtual Private Network traps";
            type empty;
          }
          leaf msdp {
            tailf:info
              "Allow SNMP MSDP traps";
            type empty;
          }
          leaf mvpn {
            tailf:info
              "Allow Multicast Virtual Private Network traps";
            type empty;
          }
          leaf nhrp {
            tailf:info
              "Allow SNMP NHRP traps";
            type empty;
          }
          leaf ospf {
            tailf:info
              "Allow OSPF traps";
            type empty;
          }
          leaf ospfv3 {
            tailf:info
              "Allow OSPFv3 traps";
            type empty;
          }
          leaf pfr {
            tailf:info
              "Allow SNMP PfR traps";
            type empty;
          }
          leaf pim {
            tailf:info
              "Allow SNMP PIM traps";
            type empty;
          }
          leaf pw-vc {
            tailf:info
              "Allow SNMP Pseudowire VC traps";
            type empty;
          }
          leaf resource-policy {
            tailf:info
              "Enable CISCO-ERM-MIB notifications";
            type empty;
          }
          leaf rf {
            tailf:info
              "Allow all SNMP traps defined in CISCO-RF-MIB";
            type empty;
          }
          leaf rsrb {
            tailf:info
              "Allow rsrb event traps";
            type empty;
          }
          leaf rsvp {
            tailf:info
              "Allow RSVP flow change traps";
            type empty;
          }
          leaf sdlc {
            tailf:info
              "Allow sdlc event traps";
            type empty;
          }
          leaf sdllc {
            tailf:info
              "Allow sdllc event traps";
            type empty;
          }
          leaf snmp {
            tailf:info
              "Allow SNMP-type notifications";
            type empty;
          }
          leaf sonet {
            tailf:info
              "Allow SNMP SONET traps";
            type empty;
          }
          leaf srp {
            tailf:info
              "Allow SRP protocol traps";
            type empty;
          }
          leaf stun {
            tailf:info
              "Allow stun event traps";
            type empty;
          }
          leaf syslog {
            tailf:info
              "Allow SNMP syslog traps";
            type empty;
          }
          leaf trustsec-sxp {
            tailf:info
              "Allow SNMP CISCO-TRUSTSEC-SXP-MIB traps";
            type empty;
          }
          leaf tty {
            tailf:info
              "Allow TCP connection traps";
            type empty;
          }
          leaf udp-port {
            tailf:info
              "The notification host's UDP port number (default port 162)";
            type empty;
          }
          leaf voice {
            tailf:info
              "Allow SNMP Voice traps";
            type empty;
          }
          leaf vrfmib {
            tailf:info
              "Allow SNMP vrfmib traps";
            type empty;
          }
          leaf vrrp {
            tailf:info
              "Allow SNMP vrrp traps";
            type empty;
          }
          leaf x25 {
            tailf:info
              "Allow x25 event traps";
            type empty;
          }
        }
      }
      container ip {
        tailf:info
          "IP ToS configuration for SNMP traffic";
        leaf precedence {
          tailf:info
            "IP Precedence value for SNMP traffic";
          tailf:cli-full-command;
          type uint8 {
            tailf:info
              "<0-7>;;ip precedence value (default value 0)";
            range "0..7";
          }
        }
      }
      container ifindex {
        tailf:info
          "Enable ifindex persistence";
        leaf persist {
          tailf:info
            "Persist interface indices";
          type empty;
        }
      }
      leaf location {
        tailf:info
          "Text for mib object sysLocation";
        tailf:cli-multi-value;
        type string {
          tailf:info
            "LINE;;The physical location of this node";
        }
      }
      container manager {
        tailf:info
          "Modify SNMP manager parameters";
        tailf:cli-display-separated;
        presence "true";
        leaf session-timeout {
          tailf:info
            "Timeout value for destroying sessions";
          type uint32 {
            tailf:info
              "<10-2147483>;;seconds";
            range "10..2147483";
          }
        }
      }
      leaf queue-length {
        tailf:info
          "Message queue length for each TRAP host";
        type uint16 {
          tailf:info
            "<1-5000>;;Queue length (default 10)";
          range "1..5000";
        }
      }
      container source-interface {
        tailf:info
          "Assign an source interface";
        container informs {
          tailf:info
            "source interface for informs";
          tailf:cli-diff-dependency "/ios:interface" {
            tailf:xpath-root 3;
          }
          uses interface-grouping;
        }
        container traps {
          tailf:info
            "source interface for traps";
          tailf:cli-diff-dependency "/ios:interface" {
            tailf:xpath-root 3;
          }
          uses interface-grouping;
        }
      }
      container trap {
        tailf:info
          "SNMP trap options";
        leaf timeout {
          tailf:info
            "Set timeout for TRAP message retransmissions";
          type uint16 {
            tailf:info
              "<1-1000>;;Timeout (default 30 seconds)";
            range "1..1000";
          }
        }
      }
      container trap-source {
        tailf:info
          "Assign an interface for the source address of all traps";
        tailf:cli-diff-dependency "/ios:interface" {
          tailf:xpath-root 3;
        }
        uses interface-grouping;
      }
      list view {
        tailf:info
          "Define an SNMPv2 MIB view";
        tailf:cli-suppress-mode;
        tailf:cli-delete-when-empty;
        tailf:cli-compact-syntax;
        key "name mib";
        leaf name {
          type string {
            tailf:info
              "WORD;;Name of the view";
          }
        }
        leaf mib {
          type string {
            tailf:info
              "WORD;;MIB view family name";
          }
        }
        leaf inc-exl {
          tailf:cli-drop-node-name;
          type enumeration {
            enum "excluded" {
              tailf:info
                "MIB family is excluded from the view";
            }
            enum "included" {
              tailf:info
                "MIB family is included in the view";
            }
          }
        }
      }
    }
    container dot11 {
      tailf:ncs-device-type "cli-ned";
      tailf:display-when "not(../../ncs:module) or ../../ncs:module[ncs:name='tailf-ned-cisco-ios']";
      tailf:info
        "IEEE 802.11 config commands";
      leaf syslog {
        tailf:info
          "Enable syslog";
        tailf:cli-full-command;
        type empty;
      }
    }
    container license {
      tailf:ncs-device-type "cli-ned";
      tailf:display-when "not(../../ncs:module) or ../../ncs:module[ncs:name='tailf-ned-cisco-ios']";
      tailf:info
        "Configure license features";
      container udi {
        tailf:cli-compact-syntax;
        tailf:cli-sequence-commands;
        tailf:cli-reset-container;
        leaf pid {
          type string;
        }
        leaf sn {
          type string;
        }
      }
      container boot {
        tailf:info
          "license boot config commands";
        container level {
          tailf:info
            "which level to boot";
          container ipbase {
            tailf:info
              "ipbase level";
            tailf:cli-display-separated;
            presence "true";
            leaf switch {
              tailf:info
                "Switch license information";
              type uint8;
            }
          }
          container ipservices {
            tailf:info
              "ipservices level";
            tailf:cli-display-separated;
            presence "true";
            leaf switch {
              tailf:info
                "Switch license information";
              type empty;
            }
          }
          container lanbase {
            tailf:info
              "lanbase level";
            tailf:cli-display-separated;
            presence "true";
            leaf switch {
              tailf:info
                "Switch license information";
              type empty;
            }
          }
        }
      }
    }
    list voice-card {
      tailf:ncs-device-type "cli-ned";
      tailf:display-when "not(../ncs:module) or ../ncs:module[ncs:name='tailf-ned-cisco-ios']";
      tailf:info
        "Configure a specific voice-card";
      tailf:cli-mode-name "config-voicecard";
      key "slot";
      leaf slot {
        type uint8 {
          tailf:info
            "<0-2>;;Voice interface slot #";
          range "0..2";
        }
      }
    }
    container card {
      tailf:ncs-device-type "cli-ned";
      tailf:display-when "not(../../ncs:module) or ../../ncs:module[ncs:name='tailf-ned-cisco-ios']";
      tailf:cli-reset-container;
      tailf:cli-compact-syntax;
      tailf:cli-sequence-commands;
      leaf type {
        tailf:cli-incomplete-command;
        tailf:cli-remove-before-change;
        type enumeration {
          enum "t1";
          enum "e1";
        }
      }
      leaf slot {
        tailf:cli-drop-node-name;
        type uint32;
      }
      leaf bay {
        tailf:cli-drop-node-name;
        type uint32;
      }
    }
    container event {
      tailf:ncs-device-type "cli-ned";
      tailf:display-when "not(../../ncs:module) or ../../ncs:module[ncs:name='tailf-ned-cisco-ios']";
      tailf:info
        "Event related configuration commands";
      container manager {
        tailf:info
          "Event Manager configuration commands";
        list applet {
          tailf:info
            "Register an Event Manager applet";
          tailf:cli-mode-name "config-applet";
          tailf:cli-exit-command "exit" {
            tailf:info
              "Exit from Event Manager applet configuration submode";
          }
          key "name";
          leaf name {
            type string {
              tailf:info
                "WORD;;Name of the Event Manager applet";
            }
          }
          leaf authorization {
            tailf:info
              "Specify an authorization type for the applet";
            tailf:cli-hide-in-submode;
            type enumeration {
              enum "bypass" {
                tailf:info
                  "EEM aaa authorization type bypass";
              }
            }
          }
          leaf class {
            tailf:info
              "Specify a class for the applet";
            tailf:cli-hide-in-submode;
            type string {
              tailf:info
                "Class A-Z | default - default class";
              pattern '[A-Z]|default';
            }
          }
          leaf trap {
            tailf:info
              "Generate an SNMP trap when applet is triggered.";
            tailf:cli-hide-in-submode;
            type empty;
          }
          container event {
            tailf:info
              "Add or modify event information";
            container snmp-notification {
              tailf:info
                "SNMP Notification Event";
              tailf:cli-compact-syntax;
              tailf:cli-reset-container;
              leaf oid {
                tailf:info
                  "Object ID of data element";
                type string {
                  tailf:info
                    "WORD;;OID string";
                }
              }
              leaf oid-val {
                tailf:info
                  "Comparison value";
                type string {
                  tailf:info
                    "WORD;;Comparision value";
                }
              }
              leaf op {
                tailf:info
                  "Operator";
                type operator-type;
              }
              leaf src-ip-address {
                tailf:info
                  "Source ip address";
                type union {
                  type inet:ipv4-address {
                    tailf:info
                      "A.B.C.D;;Source ip address value";
                  }
                  type inet:ipv6-address {
                    tailf:info
                      "X:X:X:X::X;;Source ip address value";
                  }
                }
              }
              leaf dest-ip-address {
                tailf:info
                  "Destination ip address";
                type union {
                  type inet:ipv4-address {
                    tailf:info
                      "A.B.C.D;;Destination ip address value";
                  }
                  type inet:ipv6-address {
                    tailf:info
                      "X:X:X:X::X;;Destination ip address value";
                  }
                }
              }
            }
            container syslog {
              tailf:info
                "Syslog event";
              leaf pattern {
                tailf:info
                  "Pattern match string for the entire message";
                type string {
                  tailf:info
                    "WORD;;Pattern match string for the entire message";
                }
              }
            }
          }
          list action {
            tailf:info
              "Add or modify an action statement";
            tailf:cli-suppress-mode;
            tailf:cli-delete-when-empty;
            tailf:cli-incomplete-command;
            tailf:cli-compact-syntax;
            tailf:cli-reset-container;
            ordered-by user;
            key "name";
            leaf name {
              type string {
                tailf:info
                  "WORD;;Label";
              }
            }
            container if {
              tailf:info
                "if conditional";
              tailf:cli-compact-syntax;
              tailf:cli-sequence-commands;
              tailf:cli-reset-container;
              leaf string-op-1 {
                tailf:cli-drop-node-name;
                tailf:cli-incomplete-command;
                type string {
                  tailf:info
                    "WORD;;first operand";
                }
              }
              leaf keyword {
                tailf:cli-drop-node-name;
                tailf:cli-incomplete-command;
                type operator-type;
              }
              leaf string-op-2 {
                tailf:cli-drop-node-name;
                type string {
                  tailf:info
                    "WORD;;second operand";
                }
              }
              leaf goto {
                tailf:info
                  "goto label";
                type string {
                  tailf:info
                    "WORD;;label";
                }
              }
            }
            container info {
              tailf:info
                "Obtain system specific information";
              container type {
                tailf:info
                  "Type of information to obtain";
                tailf:cli-full-no;
                container snmp {
                  tailf:info
                    "SNMP information";
                  container var {
                    tailf:info
                      "Trap variable";
                    tailf:cli-compact-syntax;
                    tailf:cli-sequence-commands;
                    tailf:cli-reset-container;
                    leaf variable-name {
                      tailf:cli-drop-node-name;
                      tailf:cli-incomplete-command;
                      type string {
                        tailf:info
                          "WORD;;Trap variable name";
                      }
                    }
                    leaf oid {
                      tailf:info
                        "SNMP object id";
                      tailf:cli-incomplete-command;
                      type string {
                        tailf:info
                          "WORD;;oid string";
                      }
                    }
                    leaf oid-type {
                      tailf:cli-drop-node-name;
                      tailf:cli-incomplete-command;
                      type enumeration {
                        enum "counter" {
                          tailf:info
                            "Counter value";
                        }
                        enum "gauge" {
                          tailf:info
                            "Gauge value";
                        }
                        enum "int" {
                          tailf:info
                            "Integer value";
                        }
                        enum "ipv4" {
                          tailf:info
                            "IPv4 address";
                        }
                        enum "octet" {
                          tailf:info
                            "Octet value";
                        }
                        enum "string" {
                          tailf:info
                            "String value";
                        }
                        enum "uint" {
                          tailf:info
                            "Unsigned integer value";
                        }
                      }
                    }
                    leaf oid-type-value {
                      tailf:cli-drop-node-name;
                      type string;
                    }
                  }
                  container trap {
                    tailf:info
                      "SNMP trap";
                    tailf:cli-compact-syntax;
                    tailf:cli-sequence-commands;
                    tailf:cli-reset-container;
                    leaf enterprise-oid {
                      tailf:info
                        "Enterprise oid";
                      tailf:cli-incomplete-command;
                      type string {
                        tailf:info
                          "WORD;;Enterprise oid string";
                      }
                    }
                    leaf generic-trapnum {
                      tailf:info
                        "Generic trap number";
                      tailf:cli-incomplete-command;
                      type uint32 {
                        tailf:info
                          "<0-4294967295>;;Generic trap number";
                      }
                    }
                    leaf specific-trapnum {
                      tailf:info
                        "Specific trap number";
                      tailf:cli-incomplete-command;
                      type uint32 {
                        tailf:info
                          "<0-4294967295>;;Specific trap number";
                      }
                    }
                    leaf trap-oid {
                      tailf:info
                        "Trap oid";
                      tailf:cli-incomplete-command;
                      type string {
                        tailf:info
                          "WORD;;oid string";
                      }
                    }
                    leaf trap-var {
                      tailf:info
                        "Trap variable";
                      type string {
                        tailf:info
                          "WORD;;Trap variable name";
                      }
                    }
                  }
                }
              }
            }
            leaf end {
              tailf:info
                "end conditional block";
              type empty;
            }
            container regexp {
              tailf:info
                "regular expression match";
              tailf:cli-compact-syntax;
              tailf:cli-sequence-commands;
              tailf:cli-reset-container;
              leaf string-pattern {
                tailf:cli-drop-node-name;
                tailf:cli-incomplete-command;
                type string {
                  tailf:info
                    "WORD;;regular expression pattern";
                }
              }
              leaf string-input {
                tailf:cli-drop-node-name;
                type string {
                  tailf:info
                    "WORD;;input string";
                }
              }
              leaf string-match {
                tailf:cli-drop-node-name;
                type string {
                  tailf:info
                    "WORD;;match variable";
                }
              }
              leaf string-submatch1 {
                tailf:cli-drop-node-name;
                type string {
                  tailf:info
                    "WORD;;submatch variable";
                }
              }
              leaf string-submatch2 {
                tailf:cli-drop-node-name;
                type string {
                  tailf:info
                    "WORD;;submatch variable";
                }
              }
              leaf string-submatch3 {
                tailf:cli-drop-node-name;
                type string {
                  tailf:info
                    "WORD;;submatch variable";
                }
              }
            }
            container snmp-trap {
              tailf:info
                "Send an SNMP trap";
              tailf:cli-compact-syntax;
              tailf:cli-delete-when-empty;
              presence "true";
              leaf intdata1 {
                tailf:info
                  "SNMP integer data1";
                type int32 {
                  tailf:info
                    "<-2147483648 - 2147483647>;;SNMP trap integer value1";
                }
              }
              leaf intdata2 {
                tailf:info
                  "SNMP integer data2";
                type int32 {
                  tailf:info
                    "<-2147483648 - 2147483647>;;SNMP trap integer value2";
                }
              }
              leaf strdata {
                tailf:info
                  "SNMP trap string";
                type string {
                  tailf:info
                    "WORD  SNMP trap string value";
                }
              }
            }
            container string {
              tailf:info
                "string commands";
              leaf trim {
                tailf:info
                  "trim characters from both ends of string";
                type string;
              }
            }
            container syslog {
              tailf:info
                "Log a syslog message";
              tailf:cli-compact-syntax;
              leaf facility {
                tailf:info
                  "Facility string";
                type string {
                  tailf:info
                    "WORD;;facility string";
                }
              }
              leaf msg {
                tailf:info
                  "Syslog message";
                type string {
                  tailf:info
                    "WORD;;message string";
                }
              }
              leaf priority {
                tailf:info
                  "Priority of syslog message";
                type logging-level-type;
              }
            }
          }
          leaf description {
            tailf:info
              "Add or modify an applet description";
            tailf:cli-full-command;
            tailf:cli-multi-value;
            type string {
              tailf:info
                "LINE;;description";
            }
          }
          container trigger {
            tailf:info
              "Enter applet trigger configuration submode";
            tailf:cli-add-mode;
            tailf:cli-mode-name "config-applet-trigger";
          }
        }
      }
    }
    leaf disable-eadi {
      tailf:ncs-device-type "cli-ned";
      tailf:display-when "not(../../ncs:module) or ../../ncs:module[ncs:name='tailf-ned-cisco-ios']";
      tailf:cli-full-command;
      type empty;
    }
    container memory-size {
      tailf:ncs-device-type "cli-ned";
      tailf:display-when "not(../../ncs:module) or ../../ncs:module[ncs:name='tailf-ned-cisco-ios']";
      tailf:info
        "Adjust memory size by percentage";
      leaf iomem {
        tailf:info
          "I/O memory";
        type uint8 {
          tailf:info
            "<5-25>;;percentage of DRAM to use for I/O memory: 5, 10, 15, 20, 25";
          range "5..25" {
            tailf:step "5";
          }
        }
      }
    }
    container transceiver {
      tailf:ncs-device-type "cli-ned";
      tailf:display-when "not(../../ncs:module) or ../../ncs:module[ncs:name='tailf-ned-cisco-ios']";
      tailf:info
        "Select from transceiver configuration commands";
      container type {
        tailf:info
          "type keyword";
        container all {
          tailf:cli-add-mode;
          tailf:cli-mode-name "config-xcvr-type";
          tailf:cli-full-command;
          container monitoring {
            tailf:info
              "Enable/disable monitoring";
            presence "true";
            leaf interval {
              tailf:info
                "Set interval for monitoring";
              type uint16 {
                tailf:info
                  "<300-3600>;;Time interval for monitoring transceiver in seconds";
                range "300..3600";
              }
            }
          }
        }
      }
    }
  }
  augment "/ncs:devices/ncs:template/ncs:ned-id/ncs:config" {
    leaf version {
      type string;
    }
    container service {
      container pad {
        presence "true";
        leaf cmns {
          type empty;
        }
        leaf from-xot {
          type empty;
        }
        leaf to-xot {
          type empty;
        }
      }
      leaf password-encryption {
        type empty;
      }
      container timestamps {
        presence "true";
        container debug {
          container datetime {
            presence "true";
            leaf localtime {
              type empty;
            }
            leaf msec {
              type empty;
            }
            leaf show-timezone {
              type empty;
            }
            leaf year {
              type empty;
            }
          }
          leaf uptime {
            type empty;
          }
        }
        container log {
          container datetime {
            presence "true";
            leaf localtime {
              type empty;
            }
            leaf msec {
              type empty;
            }
            leaf show-timezone {
              type empty;
            }
            leaf year {
              type empty;
            }
          }
          leaf uptime {
            type empty;
          }
        }
      }
      container alignment {
        leaf detection {
          type empty;
        }
        leaf logging {
          type empty;
        }
      }
      leaf call-home {
        type empty;
      }
      leaf compress-config {
        type empty;
      }
      leaf config {
        type empty;
      }
      container counters {
        container max {
          leaf age {
            type string;
          }
        }
      }
      leaf dhcp {
        type empty;
      }
      leaf disable-ip-fast-frag {
        type empty;
      }
      leaf exec-callback {
        type empty;
      }
      leaf exec-wait {
        type empty;
      }
      leaf finger {
        type empty;
      }
      container heartbeat {
        leaf fatal-count {
          type string;
        }
        leaf interrupt-interval {
          type string;
        }
        leaf interrupt-max {
          type string;
        }
        leaf transmit-interval {
          type string;
        }
        leaf warning-timeout {
          type string;
        }
      }
      leaf hide-telnet-addresses {
        type empty;
      }
      leaf linenumber {
        type empty;
      }
      leaf nagle {
        type empty;
      }
      leaf old-slip-prompts {
        type empty;
      }
      leaf pt-vty-logging {
        type empty;
      }
      leaf sequence-numbers {
        type empty;
      }
      leaf slave-log {
        type empty;
      }
      leaf tcp-keepalives-in {
        type empty;
      }
      leaf tcp-keepalives-out {
        type empty;
      }
      leaf unsupported-transceiver {
        type empty;
      }
    }
    container platform {
      leaf atm-cdvt {
        type string;
      }
      container bfd {
        leaf disable-offload {
          type empty;
        }
        leaf allow-svi {
          type empty;
        }
        leaf enable-offload {
          type empty;
        }
      }
      container console {
        presence "true";
        leaf output {
          tailf:cli-drop-node-name;
          type string;
        }
      }
      container hardware {
        container throughput {
          choice throughput-choice {
            leaf disable {
              type string;
            }
            container level {
              leaf kbps {
                tailf:cli-drop-node-name;
                type string;
              }
              leaf eval-only {
                type empty;
              }
            }
          }
        }
      }
      container ipsec {
        leaf fips-mode {
          type empty;
        }
        leaf gdoi {
          type string;
        }
        container llq {
          leaf qos-group {
            type string;
          }
        }
        container reassemble {
          leaf transit {
            type empty;
          }
        }
      }
      container multicast {
        container mgre {
          leaf injection {
            type empty;
          }
        }
        container oce {
          container flag {
            leaf suppress {
              type empty;
            }
          }
        }
      }
      container punt-keepalive {
        leaf disable-kernel-core {
          type string;
        }
        container settings {
          leaf fatal-count {
            type string;
          }
          leaf transmit-interval {
            type string;
          }
          leaf warning-count {
            type string;
          }
        }
      }
      container punt-policer {
        leaf cause {
          tailf:cli-drop-node-name;
          type string;
        }
        leaf max-rate {
          tailf:cli-drop-node-name;
          type string;
        }
        leaf high {
          type empty;
        }
      }
      container qos {
        leaf marker-statistics {
          type empty;
        }
        container match-statistics {
          leaf per-filter {
            type empty;
          }
        }
        leaf performance-monitor {
          type empty;
        }
      }
      container reload {
        leaf immediate {
          type empty;
        }
      }
      leaf shell {
        type string;
      }
    }
    leaf hostname {
      type string;
    }
    container enable {
      container password {
        uses ncs_template_password-07-grouping;
      }
      leaf last-resort {
        type string;
      }
      container secret {
        leaf level {
          type string;
        }
        leaf type {
          tailf:cli-drop-node-name;
          type string;
        }
        leaf secret {
          tailf:cli-drop-node-name;
          type string;
        }
      }
      leaf use-tacacs {
        type empty;
      }
    }
    container archive {
      container log {
        container config {
          leaf hidekeys {
            type empty;
          }
        }
      }
    }
    list username {
      // NCS patched for predictable order
      ordered-by user;
      tailf:cli-suppress-mode;
      key "name";
      leaf name {
        type string;
      }
      container password {
        leaf encryption {
          tailf:cli-drop-node-name;
          type string;
        }
        leaf password {
          tailf:cli-drop-node-name;
          type string;
        }
      }
      leaf privilege {
        type string;
      }
      container secret {
        leaf encryption {
          tailf:cli-drop-node-name;
          type string;
        }
        leaf secret {
          tailf:cli-drop-node-name;
          type string;
        }
      }
    }
    list controller {
      // NCS patched for predictable order
      ordered-by user;
      key "name number";
      leaf name {
        type string;
      }
      leaf number {
        type string;
      }
      leaf framing {
        type string;
      }
      container clock {
        container source {
          choice source-choice {
            container line {
              presence "true";
              leaf line-mode {
                tailf:cli-drop-node-name;
                type string;
              }
            }
            leaf internal {
              type empty;
            }
            leaf loop-timed {
              type empty;
            }
          }
        }
      }
      leaf linecode {
        type string;
      }
      container cablelength {
        choice cablelength-choice {
          leaf long {
            type string;
          }
          leaf short {
            type string;
          }
        }
      }
      list channel-group {
        // NCS patched for predictable order
        ordered-by user;
        tailf:cli-suppress-mode;
        key "number";
        leaf number {
          type string;
        }
        leaf-list timeslots {
          // NCS patched for predictable order
          ordered-by user;
          tailf:cli-range-list-syntax;
          type string;
        }
      }
    }
    container vrf {
      list definition {
        // NCS patched for predictable order
        ordered-by user;
        key "name";
        leaf name {
          type string;
        }
        leaf description {
          type string;
        }
        leaf rd {
          type string;
        }
        container address-family {
          container ipv4 {
            presence "true";
            container export {
              leaf map {
                type string;
              }
            }
            container mdt {
              container default {
                leaf address {
                  tailf:cli-drop-node-name;
                  type string;
                }
                container mpls {
                  leaf mldp {
                    type string;
                  }
                }
              }
              container data {
                list multicast {
                  // NCS patched for predictable order
                  ordered-by user;
                  tailf:cli-drop-node-name;
                  tailf:cli-suppress-mode;
                  key "address wildcard";
                  leaf address {
                    type string;
                  }
                  leaf wildcard {
                    type string;
                  }
                }
                leaf list {
                  type ncs_template_ext-acl-type;
                }
                leaf threshold {
                  type string;
                }
              }
              leaf log-reuse {
                type empty;
              }
              leaf-list preference {
                // NCS patched for predictable order
                ordered-by user;
                type string;
              }
            }
            container route-target {
              uses ncs_template_vrf-route-target-grouping;
            }
          }
          container ipv6 {
            presence "true";
            container route-target {
              uses ncs_template_vrf-route-target-grouping;
            }
          }
        }
        container route-target {
          uses ncs_template_vrf-route-target-grouping;
        }
      }
    }
    container ip {
      leaf subnet-zero {
        type empty;
      }
      list vrf {
        // NCS patched for predictable order
        ordered-by user;
        key "name";
        leaf name {
          type string;
        }
        container bgp {
          container next-hop {
            leaf Loopback {
              type string;
            }
          }
        }
        leaf context {
          type string;
        }
        leaf description {
          type string;
        }
        container export {
          leaf map {
            type string;
          }
        }
        container import {
          choice import-choice {
            leaf map {
              type string;
            }
            container ipv4 {
              leaf ipv4-type {
                tailf:cli-drop-node-name;
                type string;
              }
              leaf upper-limit {
                tailf:cli-drop-node-name;
                type string;
              }
              leaf map {
                type string;
              }
            }
          }
        }
        container maximum {
          presence "Maximum number of routes allowed in this routing table";
          leaf routes {
            type string;
          }
          choice maximum-choice {
            // NCS drop mandatory statement
            case threshold-case {
              leaf threshold {
                tailf:cli-drop-node-name;
                type string;
              }
              leaf reinstall {
                type string;
              }
            }
            case warning-case {
              leaf warning-only {
                type empty;
              }
            }
          }
        }
        container mdt {
          presence "Backbone Multicast Distribution Tree";
          leaf default {
            type string;
          }
          leaf log-reuse {
            type empty;
          }
          container data {
            leaf mulicast-address {
              tailf:cli-drop-node-name;
              type string;
            }
            leaf wildcard-bits {
              tailf:cli-drop-node-name;
              type string;
            }
            choice mdt-data-choice {
              case mdt-data-threshold {
                leaf threshold {
                  type string;
                }
                leaf threshold-list {
                  tailf:alt-name "list";
                  type ncs_template_mdt-data-list-type;
                }
              }
              case mdt-data-list {
                leaf list {
                  type ncs_template_mdt-data-list-type;
                }
              }
            }
          }
        }
        leaf rd {
          type ncs_template_rd-type;
        }
        list route-target {
          // NCS patched for predictable order
          ordered-by user;
          tailf:cli-suppress-mode;
          key "direction target";
          leaf direction {
            type string;
          }
          leaf target {
            type ncs_template_rd-type;
          }
        }
        container vpn {
          leaf id {
            type ncs_template_vpn-id-type;
          }
        }
      }
      container mcr-conf {
        tailf:cli-drop-node-name;
        leaf multicast-routing {
          type empty;
        }
      }
      container multicast-routing {
        // NCS drop tailf-common:cli-diff-dependency statement
        // NCS drop tailf-common:cli-diff-dependency statement
        // NCS drop tailf-common:cli-diff-dependency statement
        list vrf {
          // NCS patched for predictable order
          ordered-by user;
          tailf:cli-suppress-mode;
          // NCS drop tailf-common:cli-diff-dependency statement
          key "name";
          leaf name {
            type string;
          }
          leaf distributed {
            type empty;
          }
        }
        leaf distributed {
          type empty;
        }
      }
      container as-path {
        list access-list {
          // NCS patched for predictable order
          ordered-by user;
          tailf:cli-suppress-mode;
          key "name";
          leaf name {
            type string;
          }
          list as-path-rule {
            // NCS patched for predictable order
            ordered-by user;
            tailf:cli-suppress-mode;
            tailf:cli-drop-node-name;
            key "operation rule";
            leaf operation {
              tailf:cli-drop-node-name;
              type string;
            }
            leaf rule {
              tailf:cli-drop-node-name;
              type string;
            }
          }
        }
      }
      container local {
        list pool {
          // NCS patched for predictable order
          ordered-by user;
          tailf:cli-suppress-mode;
          key "id";
          leaf id {
            type string;
          }
          leaf start {
            tailf:cli-drop-node-name;
            type string;
          }
          leaf last {
            tailf:cli-drop-node-name;
            type string;
          }
          leaf group {
            type string;
          }
        }
      }
      container cef {
        presence "true";
        leaf distributed {
          type empty;
        }
      }
      leaf classless {
        type empty;
      }
      container community-list {
        list number-standard {
          // NCS patched for predictable order
          ordered-by user;
          tailf:cli-drop-node-name;
          tailf:cli-suppress-mode;
          key "no";
          leaf no {
            type string;
          }
          uses ncs_template_ip-community-list-standard-grouping;
        }
        list number-expanded {
          // NCS patched for predictable order
          ordered-by user;
          tailf:cli-drop-node-name;
          tailf:cli-suppress-mode;
          key "no";
          leaf no {
            type string;
          }
          uses ncs_template_ip-community-list-expanded-grouping;
        }
        list expanded {
          // NCS patched for predictable order
          ordered-by user;
          tailf:cli-suppress-mode;
          key "name";
          leaf name {
            type string;
          }
          uses ncs_template_ip-community-list-expanded-grouping;
        }
        list standard {
          // NCS patched for predictable order
          ordered-by user;
          tailf:cli-suppress-mode;
          key "name";
          leaf name {
            type string;
          }
          uses ncs_template_ip-community-list-standard-grouping;
        }
      }
      container domain {
        leaf list {
          type string;
        }
        leaf lookup {
          type string;
          // NCS drop default statement
        }
        container lookup-settings {
          tailf:cli-drop-node-name;
          container lookup {
            leaf nsap {
              type empty;
            }
            container source-interface {
              // NCS drop tailf-common:cli-diff-dependency statement
              uses ncs_template_interface-grouping;
            }
          }
          leaf name {
            type string;
          }
        }
        leaf name {
          type string;
        }
      }
      container domain-lookup {
        presence "true";
        leaf nsap {
          type empty;
        }
        container source-interface {
          // NCS drop tailf-common:cli-diff-dependency statement
          uses ncs_template_interface-grouping;
        }
      }
      leaf domain-name {
        type string;
      }
      container dns {
        container server {
          presence "true";
        }
      }
      leaf default-gateway {
        type string;
      }
      container dhcp {
        list class {
          // NCS patched for predictable order
          ordered-by user;
          key "id";
          leaf id {
            type string;
          }
          container relay {
            container agent {
              leaf information {
                type empty;
              }
            }
          }
          leaf remark {
            type string;
          }
        }
        list pool {
          // NCS patched for predictable order
          ordered-by user;
          key "id";
          leaf id {
            type string;
          }
        }
        leaf smart-relay {
          type empty;
        }
        container snooping {
          presence "true";
          container information {
            container option {
              presence "true";
              leaf allow-untrusted {
                type empty;
              }
              container format {
                container remote-id {
                  choice remote-id-choice {
                    leaf hostname {
                      type empty;
                    }
                    leaf string {
                      type string;
                    }
                  }
                }
              }
            }
          }
          container track {
            leaf host {
              type empty;
            }
          }
          container verify {
            leaf mac-address {
              type empty;
            }
            leaf no-relay-agent-address {
              type empty;
            }
          }
          leaf-list vlan {
            // NCS patched for predictable order
            ordered-by user;
            type string;
          }
        }
      }
      container flow-cache {
        container timeout {
          leaf active {
            type string;
          }
        }
      }
      container flow-export {
        container destination {
          leaf ip {
            tailf:cli-drop-node-name;
            type ncs_template_host-type;
          }
          leaf port {
            tailf:cli-drop-node-name;
            type string;
          }
        }
        container source {
          // NCS drop tailf-common:cli-diff-dependency statement
          uses ncs_template_interface-grouping;
        }
        leaf version {
          type string;
        }
      }
      container forward-protocol {
        choice protocol-choice {
          leaf protocol {
            tailf:cli-drop-node-name;
            type string;
          }
          container spanning-tree {
            presence "true";
            leaf any-local-broadcast {
              type empty;
            }
          }
          leaf udp {
            type string;
          }
        }
      }
      container ftp {
        container source-interface {
          // NCS drop tailf-common:cli-diff-dependency statement
          uses ncs_template_interface-grouping;
        }
        leaf passive {
          type empty;
        }
        container password {
          uses ncs_template_password-grouping;
        }
        leaf username {
          type string;
        }
      }
      container telnet {
        leaf source-interface {
          type string;
        }
      }
      container http {
        leaf access-class {
          type string;
        }
        container authentication {
          choice authentication-choice {
            leaf aaa {
              type empty;
            }
            leaf local {
              type empty;
            }
          }
        }
        leaf server {
          type string;
        }
        leaf secure-server {
          type string;
          // NCS drop default statement
        }
        container timeout-policy {
          leaf idle {
            type string;
          }
          leaf life {
            type string;
          }
          leaf requests {
            type string;
          }
        }
        container client {
          leaf source-interface {
            type string;
          }
        }
      }
      container igmp {
        container snooping {
          presence "true";
          leaf l2-entry-limit {
            type string;
          }
        }
      }
      container multicast {
        leaf multipath {
          type empty;
        }
      }
      container nat {
        // NCS drop tailf-common:cli-diff-dependency statement
        // NCS drop tailf-common:cli-diff-dependency statement
        // NCS drop tailf-common:cli-diff-dependency statement
        list pool {
          // NCS patched for predictable order
          ordered-by user;
          tailf:cli-suppress-mode;
          key "id";
          leaf id {
            type string;
          }
          leaf start-address {
            tailf:cli-drop-node-name;
            type string;
          }
          leaf end-address {
            tailf:cli-drop-node-name;
            // NCS drop when statement
            type string;
          }
          choice prefix-choice {
            leaf netmask {
              type string;
            }
            leaf prefix-length {
              type string;
            }
          }
          leaf accounting {
            type string;
          }
          choice nat-choice {
            leaf arp-ping {
              type empty;
            }
            leaf type {
              type string;
            }
            leaf add-route {
              type empty;
            }
          }
        }
        container inside {
          container source {
            list list {
              // NCS patched for predictable order
              ordered-by user;
              tailf:cli-suppress-mode;
              key "id";
              leaf id {
                type string;
              }
              choice pool-or-interface {
                case pool-choice {
                  leaf pool {
                    type string;
                  }
                  leaf redundancy {
                    type string;
                  }
                  leaf mapping-id {
                    type string;
                  }
                }
                case interface-choice {
                  container interface {
                    uses ncs_template_interface-grouping;
                  }
                }
              }
              leaf no-payload {
                type empty;
              }
              leaf reversible {
                type empty;
              }
              leaf vrf {
                type string;
              }
              leaf match-in-vrf {
                // NCS drop when statement
                type empty;
              }
              leaf overload {
                type empty;
              }
              leaf oer {
                type empty;
              }
            }
            container static {
              list nat-static-transport-list {
                // NCS patched for predictable order
                ordered-by user;
                tailf:cli-drop-node-name;
                tailf:cli-suppress-mode;
                key "proto local-ip local-port global-ip global-port";
                leaf proto {
                  type string;
                }
                leaf local-ip {
                  tailf:cli-drop-node-name;
                  type string;
                }
                leaf local-port {
                  tailf:cli-drop-node-name;
                  type string;
                }
                leaf global-ip {
                  tailf:cli-drop-node-name;
                  type string;
                }
                leaf global-port {
                  tailf:cli-drop-node-name;
                  type string;
                }
                leaf extendable {
                  type empty;
                }
                leaf no-alias {
                  type empty;
                }
                leaf no-payload {
                  type empty;
                }
                leaf route-map {
                  type string;
                }
                leaf reversible {
                  // NCS drop when statement
                  type empty;
                }
                leaf redundancy {
                  type string;
                }
                leaf mapping-id {
                  // NCS drop when statement
                  type string;
                }
                leaf vrf {
                  type string;
                }
                leaf match-in-vrf {
                  // NCS drop when statement
                  type empty;
                }
                leaf forced {
                  type empty;
                }
                leaf overload {
                  type empty;
                }
              }
              list nat-static-transport-interface-list {
                // NCS patched for predictable order
                ordered-by user;
                tailf:cli-drop-node-name;
                tailf:cli-suppress-mode;
                key "proto local-ip local-port";
                leaf proto {
                  type string;
                }
                leaf local-ip {
                  tailf:cli-drop-node-name;
                  type string;
                }
                leaf local-port {
                  tailf:cli-drop-node-name;
                  type string;
                }
                container interface {
                  uses ncs_template_interface-grouping;
                }
                leaf global-port {
                  tailf:cli-drop-node-name;
                  type string;
                }
              }
            }
          }
          container destination {
            list list {
              // NCS patched for predictable order
              ordered-by user;
              tailf:cli-suppress-mode;
              key "id";
              leaf id {
                type string;
              }
              leaf pool {
                type string;
              }
              leaf redundancy {
                type string;
              }
              leaf mapping-id {
                type string;
              }
            }
          }
        }
        container outside {
          list list {
            // NCS patched for predictable order
            ordered-by user;
            tailf:cli-suppress-mode;
            key "id";
            leaf id {
              type string;
            }
            leaf pool {
              type string;
            }
            leaf mapping-id {
              type string;
            }
            leaf vrf {
              type string;
            }
            leaf add-route {
              type empty;
            }
          }
          list route-map {
            // NCS patched for predictable order
            ordered-by user;
            tailf:cli-suppress-mode;
            key "id";
            leaf id {
              type string;
            }
            leaf pool {
              type string;
            }
            leaf mapping-id {
              type string;
            }
            leaf vrf {
              type string;
            }
            leaf add-route {
              type empty;
            }
          }
        }
      }
      leaf-list name-server {
        // NCS patched for predictable order
        ordered-by user;
        type string;
      }
      container pim {
        // NCS drop tailf-common:cli-diff-dependency statement
        // NCS drop tailf-common:cli-diff-dependency statement
        // NCS drop tailf-common:cli-diff-dependency statement
        container ssm {
          leaf range {
            type string;
          }
        }
        list vrf {
          // NCS patched for predictable order
          ordered-by user;
          tailf:cli-suppress-mode;
          key "id";
          leaf id {
            type string;
          }
          container rp-address {
            leaf address {
              tailf:cli-drop-node-name;
              type string;
            }
            leaf access-list {
              tailf:cli-drop-node-name;
              type string;
            }
            leaf override {
              type empty;
            }
          }
        }
      }
      container prefix-list {
        list prefixes {
          // NCS patched for predictable order
          ordered-by user;
          tailf:cli-drop-node-name;
          tailf:cli-suppress-mode;
          key "name";
          leaf name {
            type string;
          }
          leaf description {
            type string;
          }
          leaf permit {
            type ios:ncs_template_ipv4-prefix;
          }
          list seq {
            // NCS patched for predictable order
            ordered-by user;
            tailf:cli-suppress-mode;
            key "no";
            leaf no {
              type string;
            }
            container deny {
              leaf ip {
                tailf:cli-drop-node-name;
                type ios:ncs_template_ipv4-prefix;
              }
              leaf ge {
                type string;
              }
              leaf le {
                type string;
              }
            }
            container permit {
              leaf ip {
                tailf:cli-drop-node-name;
                type ios:ncs_template_ipv4-prefix;
              }
              leaf ge {
                type string;
              }
              leaf le {
                type string;
              }
            }
          }
        }
        leaf sequence-number {
          type empty;
        }
      }
      container route {
        uses ncs_template_ip-route-grouping;
        leaf profile {
          type empty;
        }
        container static {
          leaf adjust-time {
            type string;
          }
          leaf inter-vrf {
            type empty;
          }
        }
        list vrf {
          // NCS patched for predictable order
          ordered-by user;
          tailf:cli-suppress-mode;
          // NCS drop tailf-common:cli-diff-dependency statement
          // NCS drop tailf-common:cli-diff-dependency statement
          // NCS drop tailf-common:cli-diff-dependency statement
          key "name";
          leaf name {
            type string;
          }
          uses ncs_template_ip-route-grouping;
        }
      }
      leaf routing {
        type empty;
      }
      container scp {
        container server {
          leaf enable {
            type empty;
          }
        }
      }
      container sla {
        container enable {
          leaf reaction-alerts {
            type empty;
          }
        }
        leaf responder {
          type empty;
        }
      }
      container bootp {
        leaf server {
          type string;
          // NCS drop default statement
        }
      }
      leaf source-route {
        type string;
        // NCS drop default statement
      }
      container ssh {
        leaf authentication-retries {
          type string;
        }
        leaf dscp {
          type string;
        }
        container logging {
          leaf events {
            type empty;
          }
        }
        leaf precedence {
          type string;
        }
        leaf time-out {
          type string;
        }
        leaf version {
          type string;
        }
      }
      container tacacs {
        container source-interface {
          // NCS drop tailf-common:cli-diff-dependency statement
          uses ncs_template_interface-grouping;
        }
      }
      container tcp {
        container path-mtu-discovery {
          presence "true";
          leaf age-timer {
            type string;
          }
        }
      }
      container tftp {
        container boot-interface {
          // NCS drop tailf-common:cli-diff-dependency statement
          uses ncs_template_interface-grouping;
        }
        container source-interface {
          // NCS drop tailf-common:cli-diff-dependency statement
          uses ncs_template_interface-grouping;
        }
      }
      container access-list {
        container standard {
          list std-named-acl {
            // NCS patched for predictable order
            ordered-by user;
            tailf:cli-drop-node-name;
            key "name";
            leaf name {
              type ncs_template_std-acl-type;
            }
            list std-access-list-rule {
              // NCS patched for predictable order
              ordered-by user;
              tailf:cli-suppress-mode;
              tailf:cli-drop-node-name;
              key "rule";
              leaf rule {
                tailf:cli-drop-node-name;
                type string;
              }
            }
          }
        }
        container extended {
          list ext-named-acl {
            // NCS patched for predictable order
            ordered-by user;
            tailf:cli-drop-node-name;
            key "name";
            leaf name {
              type string;
            }
            list ext-access-list-rule {
              // NCS patched for predictable order
              ordered-by user;
              tailf:cli-suppress-mode;
              tailf:cli-drop-node-name;
              key "rule";
              leaf rule {
                tailf:cli-drop-node-name;
                type string;
              }
            }
          }
        }
      }
    }
    container vmps {
      leaf reconfirm {
        type string;
      }
      leaf retry {
        type string;
      }
      list server {
        // NCS patched for predictable order
        ordered-by user;
        tailf:cli-suppress-mode;
        key "name";
        leaf name {
          type ncs_template_host-type;
        }
        leaf primary {
          type empty;
        }
      }
    }
    container ipv6 {
      container access-list {
        list named-acl {
          // NCS patched for predictable order
          ordered-by user;
          tailf:cli-drop-node-name;
          key "name";
          leaf name {
            type string;
          }
          list access-list-rule {
            // NCS patched for predictable order
            ordered-by user;
            tailf:cli-suppress-mode;
            tailf:cli-drop-node-name;
            key "rule";
            leaf rule {
              tailf:cli-drop-node-name;
              type string;
            }
          }
        }
      }
      leaf unicast-routing {
        type empty;
      }
      container multicast {
        container rpf {
          container backoff {
            leaf initial-delay {
              tailf:cli-drop-node-name;
              type string;
            }
            leaf max-delay {
              tailf:cli-drop-node-name;
              type string;
            }
          }
          leaf use-bgp {
            type empty;
          }
        }
      }
      container cef {
        presence "true";
        container accounting {
          leaf per-prefix {
            type empty;
          }
          leaf prefix-length {
            type empty;
          }
        }
        leaf distributed {
          type empty;
        }
      }
      container route {
        uses ncs_template_ipv6-route-grouping;
        list vrf {
          // NCS patched for predictable order
          ordered-by user;
          tailf:cli-suppress-mode;
          // NCS drop tailf-common:cli-diff-dependency statement
          // NCS drop tailf-common:cli-diff-dependency statement
          key "name";
          leaf name {
            type string;
          }
          uses ncs_template_ipv6-route-grouping;
        }
      }
      container prefix-list {
        list prefixes {
          // NCS patched for predictable order
          ordered-by user;
          tailf:cli-drop-node-name;
          tailf:cli-suppress-mode;
          key "name";
          leaf name {
            type string;
          }
          leaf description {
            type string;
          }
          leaf permit {
            type ios:ncs_template_ipv6-prefix;
          }
          list seq {
            // NCS patched for predictable order
            ordered-by user;
            tailf:cli-suppress-mode;
            key "no";
            leaf no {
              type string;
            }
            container deny {
              leaf ip {
                tailf:cli-drop-node-name;
                type ios:ncs_template_ipv6-prefix;
              }
              leaf ge {
                type string;
              }
              leaf le {
                type string;
              }
            }
            container permit {
              leaf ip {
                tailf:cli-drop-node-name;
                type ios:ncs_template_ipv6-prefix;
              }
              leaf ge {
                type string;
              }
              leaf le {
                type string;
              }
            }
          }
        }
        leaf sequence-number {
          type empty;
        }
      }
    }
    container vlan {
      container accounting;
      container internal {
        container allocation {
          leaf policy {
            type string;
          }
        }
      }
      container dot1q {
        container tag {
          leaf native {
            type empty;
          }
        }
      }
      container access-log {
        leaf maxflow {
          type string;
        }
        leaf ratelimit {
          type string;
        }
        leaf threshold {
          type string;
        }
      }
      list vlan-list {
        // NCS patched for predictable order
        ordered-by user;
        tailf:cli-drop-node-name;
        tailf:cli-range-list-syntax;
        key "id";
        leaf id {
          type string;
        }
        leaf name {
          type string;
        }
        leaf uni-vlan {
          type string;
        }
      }
    }
    container interface {
      // NCS drop tailf-common:cli-diff-dependency statement
      list Embedded-Service-Engine {
        // NCS patched for predictable order
        ordered-by user;
        key "name";
        leaf name {
          type string;
        }
        uses ncs_template_interface-common-grouping;
      }
      list FastEthernet {
        // NCS patched for predictable order
        ordered-by user;
        key "name";
        leaf name {
          type string;
        }
        uses ncs_template_interface-ethernet-grouping;
        uses ncs_template_interface-common-grouping;
        uses ncs_template_interface-zone-member-grouping;
        uses ncs_template_interface-switch-grouping;
      }
      list GigabitEthernet {
        // NCS patched for predictable order
        ordered-by user;
        key "name";
        leaf name {
          type string;
        }
        leaf media-type {
          type string;
        }
        leaf port-type {
          type string;
        }
        uses ncs_template_interface-ethernet-grouping;
        uses ncs_template_interface-common-grouping;
        uses ncs_template_interface-zone-member-grouping;
        uses ncs_template_interface-switch-grouping;
      }
      list TenGigabitEthernet {
        // NCS patched for predictable order
        ordered-by user;
        key "name";
        leaf name {
          type string;
        }
        leaf media-type {
          type string;
        }
        leaf port-type {
          type string;
        }
        uses ncs_template_interface-ethernet-grouping;
        uses ncs_template_interface-common-grouping;
        uses ncs_template_interface-zone-member-grouping;
        uses ncs_template_interface-switch-grouping;
      }
      list Loopback {
        // NCS patched for predictable order
        ordered-by user;
        key "name";
        leaf name {
          type string;
        }
        uses ncs_template_interface-common-grouping;
      }
      list Port-channel {
        // NCS patched for predictable order
        ordered-by user;
        key "name";
        leaf name {
          type string;
        }
        leaf speed {
          type string;
        }
        uses ncs_template_interface-common-grouping;
        uses ncs_template_interface-switch-grouping;
      }
      list Vlan {
        // NCS patched for predictable order
        ordered-by user;
        key "name";
        leaf name {
          type string;
        }
        uses ncs_template_interface-common-grouping;
        uses ncs_template_interface-zone-member-grouping;
      }
      list Group-Async {
        // NCS patched for predictable order
        ordered-by user;
        key "name";
        leaf name {
          type string;
        }
        leaf physical-layer {
          type string;
        }
        uses ncs_template_interface-common-grouping;
      }
      list Multilink {
        // NCS patched for predictable order
        ordered-by user;
        key "name";
        leaf name {
          type string;
        }
        uses ncs_template_interface-common-grouping;
        uses ncs_template_interface-pointtopoint-grouping;
      }
      list Serial {
        // NCS patched for predictable order
        ordered-by user;
        key "name";
        leaf name {
          type string;
        }
        uses ncs_template_interface-common-grouping;
        uses ncs_template_interface-pointtopoint-grouping;
      }
      list Virtual-Template {
        // NCS patched for predictable order
        ordered-by user;
        key "name";
        leaf name {
          type string;
        }
        uses ncs_template_interface-ethernet-grouping;
        uses ncs_template_interface-common-grouping;
        uses ncs_template_interface-zone-member-grouping;
        uses ncs_template_interface-switch-grouping;
        uses ncs_template_interface-pointtopoint-grouping;
      }
    }
    list route-map {
      // NCS patched for predictable order
      ordered-by user;
      key "name sequence";
      leaf name {
        type string;
      }
      leaf sequence {
        tailf:cli-drop-node-name;
        type string;
      }
      leaf operation {
        tailf:cli-drop-node-name;
        type string;
        // NCS drop default statement
      }
      container set {
        container as-path {
          container prepend {
            container as-container {
              tailf:cli-drop-node-name;
              leaf as-number {
                tailf:cli-drop-node-name;
                type string;
              }
            }
            container last-as-cont {
              tailf:cli-drop-node-name;
              leaf last-as {
                type string;
              }
            }
          }
          container tag {
            presence "tag";
          }
        }
        container community {
          choice community-choice {
            case community-numberi-case {
              leaf community-number {
                tailf:cli-drop-node-name;
                type string;
              }
              leaf community-number-alt-format {
                tailf:cli-drop-node-name;
                type string;
              }
            }
            case well-known-community-case {
              leaf well-known-communities {
                tailf:cli-drop-node-name;
                type string;
              }
            }
          }
          leaf additive {
            type empty;
          }
        }
        container comm-list {
          choice comm-list-choice {
            leaf comm-list-standard {
              tailf:cli-drop-node-name;
              type string;
            }
            leaf comm-list-expanded {
              tailf:cli-drop-node-name;
              type string;
            }
            leaf comm-list-name {
              tailf:cli-drop-node-name;
              type string;
            }
          }
          leaf delete {
            type empty;
          }
        }
        container extcommunity {
          leaf-list rt {
            // NCS patched for predictable order
            ordered-by user;
            type ncs_template_asn-ip-type;
          }
        }
        container ip {
          container next-hop {
            choice next-hop-choice {
              leaf-list address {
                // NCS patched for predictable order
                ordered-by user;
                tailf:cli-drop-node-name;
                type string;
              }
              container dynamic {
                leaf dhcp {
                  type empty;
                }
              }
              leaf peer-address {
                type empty;
              }
            }
          }
        }
        leaf metric {
          type string;
        }
        leaf metric-type {
          type string;
        }
        leaf weight {
          type string;
        }
        container origin {
          choice origin-choice {
            leaf origin-value {
              tailf:cli-drop-node-name;
              type string;
            }
            leaf egp {
              type string;
            }
          }
        }
      }
      container match {
        container community {
          leaf-list name {
            // NCS patched for predictable order
            ordered-by user;
            tailf:cli-drop-node-name;
            type string;
          }
        }
        container ip {
          container address {
            choice address-choice {
              leaf access-list {
                tailf:cli-drop-node-name;
                type ncs_template_exp-acl-type;
              }
              leaf prefix-list {
                type string;
              }
            }
          }
        }
        container ipv6 {
          container address {
            choice address-choice {
              leaf access-list {
                tailf:cli-drop-node-name;
                type string;
              }
              leaf prefix-list {
                type string;
              }
            }
          }
        }
      }
    }
    container authentication {
      container mac-move {
        leaf permit {
          type empty;
        }
      }
    }
    container banner {
      container exec {
        leaf start-marker {
          tailf:cli-drop-node-name;
          type string;
        }
        leaf message {
          tailf:cli-drop-node-name;
          type string;
        }
        leaf end-marker {
          tailf:cli-drop-node-name;
          type string;
          // NCS drop must statement
        }
      }
      container login {
        leaf start-marker {
          tailf:cli-drop-node-name;
          type string;
        }
        leaf message {
          tailf:cli-drop-node-name;
          type string;
        }
        leaf end-marker {
          tailf:cli-drop-node-name;
          type string;
          // NCS drop must statement
        }
      }
      container prompt-timeout {
        leaf start-marker {
          tailf:cli-drop-node-name;
          type string;
        }
        leaf message {
          tailf:cli-drop-node-name;
          type string;
        }
        leaf end-marker {
          tailf:cli-drop-node-name;
          type string;
          // NCS drop must statement
        }
      }
      container motd {
        leaf start-marker {
          tailf:cli-drop-node-name;
          type string;
        }
        leaf message {
          tailf:cli-drop-node-name;
          type string;
        }
        leaf end-marker {
          tailf:cli-drop-node-name;
          type string;
          // NCS drop must statement
        }
      }
    }
    list table-map {
      // NCS patched for predictable order
      ordered-by user;
      key "name";
      leaf name {
        type string;
      }
      leaf default {
        type string;
      }
      list map {
        // NCS patched for predictable order
        ordered-by user;
        tailf:cli-suppress-mode;
        key "from to";
        leaf from {
          type string;
        }
        leaf to {
          type string;
        }
      }
    }
    container mls {
      container acl {
        container tcam {
          leaf default-result {
            type string;
          }
          container log-update {
            presence "true";
            leaf rate-limit-msg {
              type string;
            }
          }
          leaf share-global {
            type string;
            // NCS drop default statement
          }
        }
      }
      container cef {
        container error {
          leaf action {
            type string;
          }
        }
      }
      container flow {
        leaf ip {
          type string;
        }
      }
      container ip {
        container multicast {
          presence "true";
          container consistency-check {
            presence "true";
            leaf settle-time {
              type string;
            }
          }
          leaf flow-stat-timer {
            type string;
          }
        }
      }
      container mls-qos-conf {
        tailf:cli-drop-node-name;
        leaf qos {
          type empty;
        }
      }
      container qos {
        list aggregate-policer {
          // NCS patched for predictable order
          ordered-by user;
          tailf:cli-suppress-mode;
          key "name";
          leaf name {
            type string;
          }
          leaf target-bit-rate {
            tailf:cli-drop-node-name;
            type string;
          }
          leaf burst-normal {
            tailf:cli-drop-node-name;
            type string;
          }
          leaf burst-max {
            tailf:cli-drop-node-name;
            // NCS drop when statement
            type string;
          }
          leaf pir {
            type string;
          }
          container conform-action {
            choice action-choice {
              leaf drop {
                type empty;
              }
              leaf set-dscp-transmit {
                type ncs_template_dscp-type;
              }
              leaf set-mpls-exp-imposition-transmit {
                type string;
              }
              leaf set-prec-transmit {
                type string;
              }
              leaf transmit {
                type empty;
              }
            }
          }
          leaf exceed-action {
            type string;
          }
          leaf violate-action {
            type string;
          }
        }
        container rewrite {
          container ip {
            container dscp {
              presence "true";
              leaf slot {
                type string;
              }
            }
          }
        }
      }
      container rate-limit {
        container layer2 {
          container l2pt {
            leaf packets-per-second {
              tailf:cli-drop-node-name;
              type string;
            }
            leaf packets-in-burst {
              tailf:cli-drop-node-name;
              type string;
            }
          }
          container pdu {
            leaf packets-per-second {
              tailf:cli-drop-node-name;
              type string;
            }
            leaf packets-in-burst {
              tailf:cli-drop-node-name;
              type string;
            }
          }
        }
      }
      container verify {
        container ip {
          leaf checksum {
            type string;
            // NCS drop default statement
          }
          container length {
            leaf consistent {
              type string;
              // NCS drop default statement
            }
            leaf minimum {
              type string;
              // NCS drop default statement
            }
          }
          leaf same-address {
            type empty;
          }
          leaf syslog {
            type empty;
          }
        }
      }
    }
    container policer {
      list aggregate {
        // NCS patched for predictable order
        ordered-by user;
        tailf:cli-suppress-mode;
        key "name";
        leaf name {
          type string;
        }
        leaf cir {
          type string;
        }
        leaf bc {
          type string;
        }
        leaf conform-action {
          type empty;
        }
        leaf set-qos-transmit {
          // NCS drop when statement
          type string;
        }
        leaf set-dot1ad-dei-transmit {
          // NCS drop when statement
          type string;
        }
        leaf set-prec-transmit {
          // NCS drop when statement
          type ncs_template_prec_value-type;
        }
        container set-prec-transmit-table {
          // NCS drop when statement
          tailf:cli-drop-node-name;
          leaf table {
            type string;
          }
        }
        leaf set-dscp-transmit {
          // NCS drop when statement
          type ncs_template_dscp-type;
        }
        container set-dscp-transmit-table {
          // NCS drop when statement
          tailf:cli-drop-node-name;
          leaf table {
            type string;
          }
        }
        leaf set-cos-transmit {
          // NCS drop when statement
          type ncs_template_cos_value-type;
        }
        container set-cos-transmit-table {
          // NCS drop when statement
          tailf:cli-drop-node-name;
          leaf table {
            type string;
          }
        }
        leaf transmit {
          // NCS drop when statement
          type empty;
        }
        leaf exceed-action {
          type empty;
        }
        leaf drop {
          // NCS drop when statement
          type empty;
        }
        container exceed-transmit {
          tailf:cli-drop-node-name;
          leaf transmit {
            // NCS drop when statement
            type empty;
          }
        }
      }
    }
    list class-map {
      // NCS patched for predictable order
      ordered-by user;
      key "name";
      leaf name {
        type string;
      }
      leaf type {
        type string;
      }
      leaf protocol {
        tailf:cli-drop-node-name;
        type string;
      }
      leaf prematch {
        tailf:cli-drop-node-name;
        type string;
        // NCS drop mandatory statement
      }
      leaf description {
        type string;
      }
      container match {
        uses ncs_template_class-map-match-grouping;
        container not {
          uses ncs_template_class-map-match-grouping;
        }
      }
    }
    list policy-map {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "name";
      leaf name {
        type string;
      }
      leaf type {
        type string;
      }
      leaf protocol {
        tailf:cli-drop-node-name;
        type string;
      }
      list class {
        // NCS patched for predictable order
        ordered-by user;
        key "name";
        leaf name {
          type ncs_template_class-name-type;
        }
        leaf type {
          type string;
        }
        container policy {
          // NCS drop when statement
          tailf:cli-drop-node-name;
          leaf action {
            tailf:cli-drop-node-name;
            type string;
          }
          leaf log {
            // NCS drop when statement
            type empty;
          }
          leaf parameter-map {
            tailf:cli-drop-node-name;
            // NCS drop when statement
            type string;
          }
        }
        container inspect-police {
          // NCS drop when statement
          tailf:cli-drop-node-name;
          container police {
            leaf rate {
              type string;
            }
            leaf burst {
              type string;
            }
          }
        }
        container bandwidth {
          leaf bits {
            tailf:cli-drop-node-name;
            type string;
          }
          leaf percent {
            type ncs_template_percentage-type;
          }
          container remaining {
            leaf percent {
              type ncs_template_percentage-type;
            }
          }
        }
        container compression {
          presence "Activate Compression";
          container header {
            presence "configure header compression";
            leaf ip {
              type string;
            }
          }
        }
        leaf drop {
          type empty;
        }
        container estimate {
          container bandwidth {
            presence "bandwidth required to service this class";
            container delay-one-in {
              leaf doi {
                tailf:cli-drop-node-name;
                type string;
              }
              leaf milliseconds {
                type string;
              }
            }
            leaf drop-one-in {
              type string;
            }
          }
        }
        container fair-queue {
          presence "true";
          leaf dynamic-queues {
            tailf:cli-drop-node-name;
            type string;
          }
          leaf queue-limit {
            type string;
          }
        }
        leaf netflow-sampler {
          type string;
        }
        choice police-choice {
          case police-aggregate-case {
            container police-aggregate {
              tailf:cli-drop-node-name;
              container police {
                leaf aggregate {
                  type string;
                }
              }
            }
          }
          case police-policy-map-case {
            container police-policy-map {
              tailf:cli-drop-node-name;
              container police {
                leaf cir {
                  type ncs_template_police-bps-type;
                }
                leaf bc {
                  type ncs_template_police-burst-type;
                }
                leaf be {
                  // NCS drop when statement
                  type ncs_template_police-burst-type;
                }
                leaf pir {
                  type ncs_template_police-bps-type;
                }
                container pir-be {
                  // NCS drop when statement
                  tailf:cli-drop-node-name;
                  leaf be {
                    type ncs_template_police-burst-type;
                  }
                }
                uses ncs_template_police-action-grouping;
              }
            }
          }
          case police-cir-percent-case {
            container police-cir-percent {
              tailf:cli-drop-node-name;
              container police {
                container cir {
                  container percent {
                    leaf percentage {
                      tailf:cli-drop-node-name;
                      type ncs_template_percentage-type;
                    }
                    leaf bc {
                      type string;
                    }
                    container bc-ms {
                      // NCS drop when statement
                      tailf:cli-drop-node-name;
                      leaf ms {
                        type empty;
                      }
                    }
                    leaf be {
                      // NCS drop when statement
                      type string;
                    }
                    container be-ms {
                      // NCS drop when statement
                      tailf:cli-drop-node-name;
                      leaf ms {
                        type empty;
                      }
                    }
                    container pir {
                      leaf percent {
                        type ncs_template_percentage-type;
                      }
                    }
                    container pir-be {
                      // NCS drop when statement
                      tailf:cli-drop-node-name;
                      leaf be {
                        type string;
                      }
                    }
                    container pir-be-ms {
                      // NCS drop when statement
                      tailf:cli-drop-node-name;
                      leaf ms {
                        type empty;
                      }
                    }
                    uses ncs_template_police-action-grouping;
                  }
                }
              }
            }
          }
          case police-rate-unit-case {
            container police-rate-unit {
              tailf:cli-drop-node-name;
              container police {
                container rate {
                  leaf units {
                    tailf:cli-drop-node-name;
                    type string;
                  }
                  leaf xps {
                    tailf:cli-drop-node-name;
                    type ncs_template_police-pps-bps-type;
                  }
                  container burst {
                    leaf burst-value {
                      tailf:cli-drop-node-name;
                      type string;
                    }
                    leaf burst-type {
                      tailf:cli-drop-node-name;
                      type ncs_template_police-packets-bytes-type;
                    }
                  }
                  container peak-rate {
                    leaf peak-rate-value {
                      tailf:cli-drop-node-name;
                      type string;
                    }
                    leaf xps {
                      tailf:cli-drop-node-name;
                      type ncs_template_police-pps-bps-type;
                    }
                  }
                  container peak-burst {
                    leaf burst-value {
                      tailf:cli-drop-node-name;
                      type string;
                    }
                    leaf burst-type {
                      tailf:cli-drop-node-name;
                      type ncs_template_police-packets-bytes-type;
                    }
                  }
                  uses ncs_template_police-action-grouping;
                }
              }
            }
          }
          case police-rate-percent-case {
            container police-rate-percent {
              tailf:cli-drop-node-name;
              container police {
                container rate {
                  container percent {
                    leaf percentage {
                      tailf:cli-drop-node-name;
                      type ncs_template_percentage-type;
                    }
                    leaf burst {
                      type string;
                    }
                    leaf ms {
                      // NCS drop when statement
                      type empty;
                    }
                    container peak-rate {
                      leaf percent {
                        type ncs_template_percentage-type;
                      }
                    }
                    leaf peak-burst {
                      type string;
                    }
                    container peak-burst-ms {
                      // NCS drop when statement
                      tailf:cli-drop-node-name;
                      leaf ms {
                        type empty;
                      }
                    }
                    uses ncs_template_police-action-grouping;
                  }
                }
              }
            }
          }
          case police-rate-pdp-case {
            container police-rate-pdp {
              tailf:cli-drop-node-name;
              container police {
                container rate {
                  container pdp {
                    leaf burst {
                      type ncs_template_police-burst-type;
                    }
                    leaf peak-rate {
                      type string;
                    }
                    leaf peak-burst {
                      // NCS drop when statement
                      type ncs_template_police-burst-type;
                    }
                    uses ncs_template_police-action-grouping;
                  }
                }
              }
            }
          }
          case police-flow-case {
            container police-flow {
              tailf:cli-drop-node-name;
              container police {
                container flow {
                  leaf mask {
                    type string;
                  }
                  leaf bps {
                    tailf:cli-drop-node-name;
                    type ncs_template_police-bps-type;
                  }
                  leaf burst-normal {
                    // NCS drop when statement
                    tailf:cli-drop-node-name;
                    type ncs_template_police-burst-type;
                  }
                  uses ncs_template_police-action-grouping;
                }
              }
            }
          }
          case police-catalyst-case {
            container police-catalyst {
              tailf:cli-drop-node-name;
              container police {
                leaf bps-value {
                  tailf:cli-drop-node-name;
                  type string;
                }
                leaf bps {
                  type empty;
                }
                leaf byte-value {
                  tailf:cli-drop-node-name;
                  type string;
                }
                leaf byte {
                  type empty;
                }
                container actions {
                  tailf:cli-drop-node-name;
                  uses ncs_template_police-conform-action-grouping;
                  uses ncs_template_police-exceed-action-grouping;
                  uses ncs_template_police-violate-action-grouping;
                }
              }
            }
          }
          case police-switch-case {
            container police-switch {
              tailf:cli-drop-node-name;
              container police {
                leaf cir {
                  tailf:cli-drop-node-name;
                  type string;
                }
                leaf bc {
                  tailf:cli-drop-node-name;
                  type string;
                }
                leaf exceed-action {
                  type string;
                }
              }
            }
          }
        }
        container priority {
          presence "true";
          leaf level {
            type string;
          }
          choice priority-type {
            leaf kilo-bits {
              tailf:cli-drop-node-name;
              type string;
            }
            leaf percent {
              type string;
            }
          }
          leaf burst {
            tailf:cli-drop-node-name;
            type string;
          }
        }
        container queue-limit {
          leaf queue-limit-value {
            tailf:cli-drop-node-name;
            type string;
          }
          leaf queue-limit-type {
            tailf:cli-drop-node-name;
            type string;
          }
        }
        container random-detect {
          presence "true";
          container aggregate {
            presence "true";
            leaf minimum-thresh {
              type string;
            }
            leaf maximum-thresh {
              type string;
            }
            leaf mark-probability {
              type empty;
            }
            leaf denominator {
              tailf:cli-drop-node-name;
              type string;
            }
          }
          container discard-class {
            leaf dclass {
              tailf:cli-drop-node-name;
              type string;
            }
            uses ncs_template_random-detect-grouping;
          }
          leaf discard-class-based {
            type empty;
          }
          container dscp {
            leaf dscp-val {
              tailf:cli-drop-node-name;
              type ncs_template_dscp-type;
            }
            uses ncs_template_random-detect-grouping;
          }
          leaf dscp-based {
            type empty;
          }
          leaf ecn {
            type empty;
          }
          leaf exponential-weighting-constant {
            type string;
          }
          leaf prec-based {
            type empty;
          }
          container precedence {
            leaf prec {
              tailf:cli-drop-node-name;
              type ncs_template_precedence-type2;
            }
            uses ncs_template_random-detect-grouping;
          }
        }
        leaf service-policy {
          type string;
        }
        container set {
          leaf atm-clp {
            type empty;
          }
          container cos {
            choice cos-type {
              case a {
                leaf val {
                  tailf:cli-drop-node-name;
                  type string;
                }
              }
              case b {
                leaf pack {
                  tailf:cli-drop-node-name;
                  type string;
                }
                leaf table {
                  type string;
                }
              }
            }
          }
          leaf discard-class {
            type string;
          }
          leaf dscp {
            type ncs_template_dscp-type;
          }
          leaf fr-de {
            type empty;
          }
          container ip {
            choice ip-choice {
              leaf dscp {
                type ncs_template_dscp-type;
              }
              container precedence {
                presence "Set IP precedence";
                leaf precedence-val {
                  tailf:cli-drop-node-name;
                  type ncs_template_precedence-type;
                }
              }
            }
          }
          container mpls {
            container experimental {
              container imposition {
                leaf exp-value {
                  tailf:cli-drop-node-name;
                  type string;
                }
              }
            }
          }
          container qos-group {
            leaf qos-group-value {
              tailf:cli-drop-node-name;
              type string;
            }
          }
        }
        container shape {
          leaf adaptive {
            type string;
          }
          container average {
            choice average-choice {
              case a {
                leaf bit-rate {
                  tailf:cli-drop-node-name;
                  type string;
                }
                leaf bits-per-interval-sustained {
                  tailf:cli-drop-node-name;
                  type string;
                }
                leaf bits-per-interval-excess {
                  tailf:cli-drop-node-name;
                  type string;
                }
              }
              case b {
                leaf percent {
                  type ncs_template_percentage-type;
                }
                leaf burst-size-sustained {
                  tailf:cli-drop-node-name;
                  type string;
                }
                leaf ms {
                  type empty;
                }
                container bse {
                  tailf:cli-drop-node-name;
                  leaf burst-size-excess {
                    type string;
                  }
                  leaf ms {
                    type empty;
                  }
                }
              }
            }
          }
          leaf fecn-adapt {
            type empty;
          }
          container fr-voice-adapt {
            presence "Enable rate adjustment depending on voice presence";
            leaf deactivation {
              type string;
            }
          }
          leaf max-buffers {
            type string;
          }
        }
        leaf trust {
          type string;
        }
      }
      leaf description {
        type string;
      }
    }
    container control-plane {
      presence "true";
      container service-policy {
        leaf input {
          type string;
        }
        leaf output {
          type string;
        }
      }
    }
    leaf config-register {
      type string;
    }
    container clock {
      container calendar-valid {
        presence "true";
      }
      container summer-time {
        leaf zone {
          tailf:cli-drop-node-name;
          type string;
        }
        choice summer-choice {
          case date-case {
            leaf date {
              type empty;
            }
          }
          case recurring-case {
            leaf recurring {
              type empty;
            }
            leaf start {
              tailf:cli-drop-node-name;
              type string;
            }
            leaf start-day {
              tailf:cli-drop-node-name;
              type ncs_template_weekday-type;
            }
            leaf start-month {
              tailf:cli-drop-node-name;
              type ncs_template_month-type;
            }
            leaf start-time {
              tailf:cli-drop-node-name;
              type ncs_template_hhmm-type;
            }
            leaf end {
              tailf:cli-drop-node-name;
              type string;
            }
            leaf end-day {
              tailf:cli-drop-node-name;
              type ncs_template_weekday-type;
            }
            leaf end-month {
              tailf:cli-drop-node-name;
              type ncs_template_month-type;
            }
            leaf end-time {
              tailf:cli-drop-node-name;
              type ncs_template_hhmm-type;
            }
          }
        }
      }
      container timezone {
        leaf zone {
          tailf:cli-drop-node-name;
          type string;
        }
        leaf offset {
          tailf:cli-drop-node-name;
          type string;
        }
        leaf hours {
          tailf:cli-drop-node-name;
          type string;
        }
        leaf minutes {
          tailf:cli-drop-node-name;
          type string;
        }
      }
    }
    container gatekeeper {
      leaf shutdown {
        type empty;
      }
    }
    container line {
      list aux {
        // NCS patched for predictable order
        ordered-by user;
        key "first";
        // NCS drop max-elements statement
        leaf first {
          type string;
        }
        uses ncs_template_line-grouping;
      }
      list console {
        // NCS patched for predictable order
        ordered-by user;
        key "first";
        // NCS drop max-elements statement
        leaf first {
          type string;
        }
        uses ncs_template_line-grouping;
      }
      container vty-single {
        tailf:cli-drop-node-name;
        list vty {
          // NCS patched for predictable order
          ordered-by user;
          key "first";
          leaf first {
            type string;
          }
          uses ncs_template_line-grouping;
        }
      }
      list vty {
        // NCS patched for predictable order
        ordered-by user;
        key "first last";
        leaf first {
          type string;
        }
        leaf last {
          type string;
        }
        uses ncs_template_line-grouping;
      }
    }
    container logging {
      leaf alarm {
        type string;
      }
      container buffered {
        leaf size {
          tailf:cli-drop-node-name;
          type string;
        }
        leaf severity {
          tailf:cli-drop-node-name;
          type ncs_template_logging-level-type;
        }
        leaf xxml {
          tailf:alt-name "xml";
          type string;
        }
      }
      leaf console {
        type string;
      }
      container event {
        container link-status {
          leaf boot {
            type empty;
          }
          leaf global {
            type empty;
          }
          leaf default {
            type empty;
          }
        }
      }
      container esm {
        leaf config {
          type empty;
        }
      }
      leaf facility {
        type string;
      }
      container history {
        leaf size {
          type string;
        }
        leaf severity-level {
          tailf:cli-drop-node-name;
          type string;
        }
      }
      list hostname {
        // NCS patched for predictable order
        ordered-by user;
        tailf:cli-drop-node-name;
        tailf:cli-suppress-mode;
        key "host";
        leaf host {
          type string;
        }
      }
      list host {
        // NCS patched for predictable order
        ordered-by user;
        tailf:cli-suppress-mode;
        key "host";
        leaf host {
          type string;
        }
        leaf vrf {
          type string;
        }
        leaf discriminator {
          type string;
        }
      }
      container rate-limit {
        leaf console {
          type empty;
        }
        leaf all {
          type empty;
        }
        leaf rate {
          tailf:cli-drop-node-name;
          type string;
        }
      }
      container source-interface {
        // NCS drop tailf-common:cli-diff-dependency statement
        uses ncs_template_interface-grouping;
      }
      leaf trap {
        type ncs_template_logging-level-type;
      }
    }
    container mgcp {
      container fax {
        container t38 {
          leaf ecm {
            type empty;
          }
        }
      }
      container profile {
        leaf default {
          type empty;
        }
      }
    }
    container multilink {
      leaf bundle-name {
        type string;
      }
      leaf virtual-template {
        type string;
      }
    }
    container ntp {
      // NCS drop tailf-common:cli-diff-dependency statement
      container access-group {
        leaf peer {
          type string;
        }
        leaf serve {
          type string;
        }
      }
      container server {
        uses ncs_template_ntp-server-grouping;
        list vrf {
          // NCS patched for predictable order
          ordered-by user;
          tailf:cli-suppress-mode;
          // NCS drop tailf-common:cli-diff-dependency statement
          // NCS drop tailf-common:cli-diff-dependency statement
          key "name";
          leaf name {
            type string;
          }
          uses ncs_template_ntp-server-grouping;
        }
      }
      container source {
        uses ncs_template_interface-grouping;
      }
      leaf update-calendar {
        type empty;
      }
    }
    container no {
      container mac-address-table {
        container learning {
          list vlan {
            // NCS patched for predictable order
            ordered-by user;
            tailf:cli-suppress-mode;
            key "id";
            leaf id {
              type string;
            }
            leaf module {
              type string;
            }
          }
        }
      }
    }
    container privilege {
      container exec {
        list level {
          // NCS patched for predictable order
          ordered-by user;
          tailf:cli-suppress-mode;
          key "privilege";
          leaf privilege {
            type string;
          }
          list command-list {
            // NCS patched for predictable order
            ordered-by user;
            tailf:cli-suppress-mode;
            tailf:cli-drop-node-name;
            key "command";
            leaf command {
              tailf:cli-drop-node-name;
              type string;
            }
          }
        }
      }
    }
    container redundancy {
      leaf maintenance-mode {
        type empty;
      }
      container main-cpu {
        container auto-sync {
          leaf running-config {
            type empty;
          }
          leaf config-register {
            type empty;
          }
          leaf bootvar {
            type empty;
          }
        }
      }
      leaf mode {
        type string;
      }
    }
    container scheduler {
      container allocate {
        leaf interrupt-time {
          tailf:cli-drop-node-name;
          type string;
        }
        leaf process-time {
          tailf:cli-drop-node-name;
          type string;
        }
      }
    }
    container spanning-tree {
      container etherchannel {
        container guard {
          leaf misconfig {
            type empty;
          }
        }
      }
      container extend {
        leaf system-id {
          type empty;
        }
      }
      container loopguard {
        leaf default {
          type empty;
        }
      }
      container mst {
        list instance-range {
          // NCS patched for predictable order
          ordered-by user;
          tailf:cli-suppress-mode;
          tailf:cli-drop-node-name;
          tailf:cli-range-list-syntax;
          key "id";
          leaf id {
            type string;
          }
          leaf priority {
            type string;
          }
        }
        container configuration {
          leaf name {
            type string;
          }
          list instance {
            // NCS patched for predictable order
            ordered-by user;
            tailf:cli-suppress-mode;
            key "id";
            leaf id {
              type string;
            }
            leaf-list vlan {
              // NCS patched for predictable order
              ordered-by user;
              tailf:cli-range-list-syntax;
              type string;
            }
          }
        }
      }
      container optimize {
        container bpdu {
          leaf transmission {
            type string;
          }
        }
      }
      container portfast {
        leaf bdpu {
          tailf:cli-drop-node-name;
          type string;
        }
        leaf default {
          type empty;
        }
      }
      leaf mode {
        type string;
      }
      container vlans-max-age {
        tailf:cli-drop-node-name;
        list vlan {
          // NCS patched for predictable order
          ordered-by user;
          tailf:cli-range-list-syntax;
          tailf:cli-suppress-mode;
          key "id";
          leaf id {
            type string;
          }
          leaf max-age {
            type string;
          }
        }
      }
      container vlans-forward-time {
        tailf:cli-drop-node-name;
        list vlan {
          // NCS patched for predictable order
          ordered-by user;
          tailf:cli-range-list-syntax;
          tailf:cli-suppress-mode;
          key "id";
          leaf id {
            type string;
          }
          leaf forward-time {
            type string;
          }
        }
      }
      container vlans-hello-time {
        tailf:cli-drop-node-name;
        list vlan {
          // NCS patched for predictable order
          ordered-by user;
          tailf:cli-range-list-syntax;
          tailf:cli-suppress-mode;
          key "id";
          leaf id {
            type string;
          }
          leaf hello-time {
            type string;
          }
        }
      }
      container vlans-priority {
        tailf:cli-drop-node-name;
        list vlan {
          // NCS patched for predictable order
          ordered-by user;
          tailf:cli-range-list-syntax;
          tailf:cli-suppress-mode;
          key "id";
          leaf id {
            type string;
          }
          leaf priority {
            type string;
          }
        }
      }
      container vlans-root {
        tailf:cli-drop-node-name;
        list vlan {
          // NCS patched for predictable order
          ordered-by user;
          tailf:cli-range-list-syntax;
          tailf:cli-suppress-mode;
          key "id";
          leaf id {
            type string;
          }
          container root {
            container primary {
              leaf diameter {
                type string;
              }
              leaf hello-time {
                type string;
              }
            }
            container secondary {
              leaf diameter {
                type string;
              }
              leaf hello-time {
                type string;
              }
            }
          }
        }
      }
    }
    container dot1x {
      container critical {
        leaf eapol {
          type empty;
        }
        container recovery {
          leaf delay {
            type string;
          }
        }
      }
      leaf system-auth-control {
        type empty;
      }
    }
    container power {
      leaf redundancy-mode {
        type string;
      }
    }
    container parameter-map {
      container type {
        list inspect {
          // NCS patched for predictable order
          ordered-by user;
          key "id";
          leaf id {
            type string;
          }
          leaf alert {
            type string;
          }
          leaf audit-trail {
            type string;
          }
          leaf dns-timeout {
            type string;
          }
          container icmp {
            leaf idle-time {
              type string;
            }
          }
          container max-incomplete {
            leaf high {
              type string;
            }
            leaf low {
              type string;
            }
          }
          container one-minute {
            leaf high {
              type string;
            }
            leaf low {
              type string;
            }
          }
          container sessions {
            leaf maximum {
              type string;
            }
          }
          container tcp {
            leaf finwait-time {
              type string;
            }
            leaf idle-time {
              type string;
            }
            container max-incomplete {
              leaf host {
                type string;
              }
            }
            leaf synwait-time {
              type string;
            }
          }
          container udp {
            leaf idle-time {
              type string;
            }
          }
        }
      }
    }
    container vpdn {
      leaf authen-before-forward {
        type empty;
      }
      leaf enable {
        type empty;
      }
      leaf-list search-order {
        // NCS patched for predictable order
        ordered-by user;
        type string;
      }
    }
    container bba-group {
      list pppoe {
        // NCS patched for predictable order
        ordered-by user;
        key "id";
        leaf id {
          type string;
        }
        container vendor-tag {
          container circuit-id {
            leaf service {
              type empty;
            }
          }
          container dsl-sync-rate {
            leaf service {
              type empty;
            }
          }
          container remote-id {
            leaf service {
              type empty;
            }
          }
          leaf strip {
            type empty;
          }
        }
        leaf virtual-template {
          type string;
        }
      }
    }
    container mac {
      container access-list {
        list extended {
          // NCS patched for predictable order
          ordered-by user;
          key "id";
          leaf id {
            type string;
          }
          container deny {
            container source {
              tailf:cli-drop-node-name;
              choice target-choice {
                leaf any {
                  type empty;
                }
                leaf host {
                  type string;
                }
              }
            }
            container dest {
              tailf:cli-drop-node-name;
              choice target-choice {
                leaf any {
                  type empty;
                }
                leaf host {
                  type string;
                }
              }
            }
          }
          container permit {
            container source {
              tailf:cli-drop-node-name;
              choice target-choice {
                leaf any {
                  type empty;
                }
                leaf host {
                  type string;
                }
              }
            }
            container dest {
              tailf:cli-drop-node-name;
              choice target-choice {
                leaf any {
                  type empty;
                }
                leaf host {
                  type string;
                }
              }
            }
          }
        }
      }
    }
    container tacacs-server {
      list host {
        // NCS patched for predictable order
        ordered-by user;
        tailf:cli-suppress-mode;
        key "name";
        leaf name {
          type ncs_template_host-type;
        }
        leaf port {
          type string;
        }
        leaf timeout {
          type string;
        }
      }
      leaf timeout {
        type string;
        // NCS drop default statement
      }
      container directed-request {
        presence "true";
        leaf restricted {
          type empty;
        }
        leaf no-truncate {
          type empty;
        }
      }
      container key {
        leaf encryption {
          tailf:cli-drop-node-name;
          type string;
        }
        leaf key {
          tailf:cli-drop-node-name;
          type string;
        }
      }
    }
    container upgrade {
      container fpd {
        leaf auto {
          type empty;
        }
        leaf path {
          type string;
        }
      }
    }
    container vtp {
      leaf file {
        type string;
      }
      leaf interface {
        type string;
      }
      leaf password {
        type string;
      }
      leaf pruning {
        type empty;
      }
      leaf version {
        type string;
      }
      leaf domain {
        type string;
      }
      leaf mode {
        type string;
      }
    }
    container rep {
      container admin {
        list vlan {
          // NCS patched for predictable order
          ordered-by user;
          key "name";
          leaf name {
            type string;
          }
        }
      }
    }
    container xconnect {
      container logging {
        container pseudowire {
          leaf status {
            type empty;
          }
        }
        leaf redundancy {
          type empty;
        }
      }
    }
    container fabric {
      container switching-mode {
        container allow {
          choice allow-choice {
            leaf bus-mode {
              type empty;
            }
            container truncated {
              presence "true";
              leaf threshold {
                type string;
              }
            }
          }
        }
        container force {
          leaf bus-mode {
            type empty;
          }
        }
      }
    }
    container port-channel {
      leaf load-balance {
        type string;
      }
    }
    container l2 {
      list vfi {
        // NCS patched for predictable order
        ordered-by user;
        tailf:cli-suppress-mode;
        key "name";
        leaf name {
          type string;
        }
        leaf point-to-point {
          type empty;
        }
      }
    }
    container l2protocol-tunnel {
      leaf cos {
        type string;
      }
      container global {
        leaf drop-threshold {
          type string;
        }
      }
    }
    container system {
      container env {
        container temperature {
          container threshold {
            leaf yellow {
              type string;
            }
          }
        }
      }
      container mtu {
        leaf size {
          tailf:cli-drop-node-name;
          type string;
        }
        leaf jumbo {
          type string;
        }
        leaf routing {
          type string;
        }
      }
    }
    container errdisable {
      container detect {
        container cause {
          leaf all {
            type empty;
          }
          leaf arp-inspection {
            type empty;
          }
          leaf bpduguard {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf loopback {
            type empty;
          }
          leaf mlacp-minlink {
            type empty;
          }
          leaf pagp-flap {
            type empty;
          }
          leaf pppoe-ia-rate-limit {
            type empty;
          }
          leaf security-violation {
            type empty;
          }
          leaf sfp-config-mismatch {
            type empty;
          }
          leaf small-frame {
            type empty;
          }
        }
      }
      container flap-setting {
        container cause {
          container dtp-flap {
            leaf max-flaps {
              type string;
            }
            leaf time {
              type string;
            }
          }
          container link-flap {
            leaf max-flaps {
              type string;
            }
            leaf time {
              type string;
            }
          }
          container pagp-flap {
            leaf max-flaps {
              type string;
            }
            leaf time {
              type string;
            }
          }
        }
      }
      container recovery {
        container cause {
          leaf all {
            type empty;
          }
          leaf arp-inspection {
            type empty;
          }
          leaf bpduguard {
            type empty;
          }
          leaf channel-misconfig {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf link-monitor-failure {
            type empty;
          }
          leaf loopback {
            type empty;
          }
          leaf mac-limit {
            type empty;
          }
          leaf mlacp-minlink {
            type empty;
          }
          container oam-remote-failure {
            presence "true";
            leaf critical-event {
              type empty;
            }
            leaf dying-gasp {
              type empty;
            }
            leaf link-fault {
              type empty;
            }
          }
          leaf pagp-flap {
            type empty;
          }
          leaf port-mode-failure {
            type empty;
          }
          leaf pppoe-ia-rate-limit {
            type empty;
          }
          leaf psp {
            type empty;
          }
          leaf psecure-violation {
            type empty;
          }
          leaf security-violation {
            type empty;
          }
          leaf sfp-config-mismatch {
            type empty;
          }
          leaf small-frame {
            type empty;
          }
          leaf storm-control {
            type empty;
          }
          leaf udld {
            type empty;
          }
          leaf unicast-flood {
            type empty;
          }
          leaf vmps {
            type empty;
          }
        }
        leaf interval {
          type string;
        }
      }
    }
    container monitor {
      container event-trace;
      list session {
        // NCS patched for predictable order
        ordered-by user;
        tailf:cli-suppress-mode;
        key "id";
        leaf id {
          type string;
        }
        container destination {
          leaf interface {
            type string;
          }
          leaf encapsulation {
            type string;
          }
          leaf ingress {
            type empty;
          }
          leaf ingress-encap {
            tailf:cli-drop-node-name;
            // NCS drop when statement
            type string;
          }
          leaf vlan {
            // NCS drop when statement
            type string;
          }
        }
        container source {
          container interface {
            // NCS drop tailf-common:cli-diff-dependency statement
            uses ncs_template_interface-grouping;
          }
          container vlan {
            leaf vlan {
              tailf:cli-drop-node-name;
              type string;
            }
            leaf direction {
              tailf:cli-drop-node-name;
              type string;
            }
          }
        }
      }
    }
    list tftp-server {
      // NCS patched for predictable order
      ordered-by user;
      tailf:cli-suppress-mode;
      key "name";
      leaf name {
        type string;
      }
    }
    container radius-server {
      list host {
        // NCS patched for predictable order
        ordered-by user;
        tailf:cli-suppress-mode;
        key "id";
        leaf id {
          type string;
        }
        leaf acct-port {
          type string;
        }
        leaf auth-port {
          type string;
        }
        leaf key {
          type string;
        }
      }
    }
    container radius {
      list filter {
        // NCS patched for predictable order
        ordered-by user;
        key "id";
        leaf id {
          type string;
        }
        leaf match {
          tailf:cli-drop-node-name;
          type string;
        }
      }
      list server {
        // NCS patched for predictable order
        ordered-by user;
        key "id";
        leaf id {
          type string;
        }
        container address {
          container ipv4 {
            leaf host {
              tailf:cli-drop-node-name;
              type string;
            }
            leaf auth-port {
              type string;
            }
            leaf acct-port {
              type string;
            }
          }
        }
        container backoff {
          container exponential {
            presence "true";
            leaf max-delay {
              type string;
            }
            leaf backoff-retry {
              type string;
            }
          }
        }
        container key {
          leaf encryption {
            tailf:cli-drop-node-name;
            type string;
          }
          leaf key {
            tailf:cli-drop-node-name;
            type string;
          }
        }
      }
    }
    container zone {
      list security {
        // NCS patched for predictable order
        ordered-by user;
        key "id";
        leaf id {
          type string;
        }
        leaf description {
          type string;
        }
      }
    }
    container zone-pair {
      list security {
        // NCS patched for predictable order
        ordered-by user;
        key "id";
        leaf id {
          type string;
        }
        leaf source {
          type string;
        }
        leaf destination {
          type string;
        }
        leaf description {
          type string;
        }
        container service-policy {
          container type {
            leaf inspect {
              type string;
            }
          }
        }
      }
    }
    container aaa {
      leaf new-model {
        type empty;
      }
      container group {
        // NCS drop tailf-common:cli-diff-dependency statement
        container server {
          list tacacsplus {
            // NCS patched for predictable order
            ordered-by user;
            tailf:alt-name "tacacs+";
            key "name";
            leaf name {
              type string;
            }
            list server-private {
              // NCS patched for predictable order
              ordered-by user;
              tailf:cli-suppress-mode;
              key "name";
              leaf name {
                type ncs_template_host-type;
              }
              leaf timeout {
                type string;
              }
              container key {
                leaf encryption {
                  tailf:cli-drop-node-name;
                  type string;
                }
                leaf key {
                  tailf:cli-drop-node-name;
                  type string;
                }
              }
            }
            container ip {
              container tacacs {
                container source-interface {
                  // NCS drop tailf-common:cli-diff-dependency statement
                  uses ncs_template_interface-grouping;
                }
              }
            }
          }
          list radius {
            // NCS patched for predictable order
            ordered-by user;
            key "name";
            leaf name {
              type string;
            }
            container server {
              list name {
                // NCS patched for predictable order
                ordered-by user;
                tailf:cli-suppress-mode;
                key "name";
                leaf name {
                  type string;
                }
              }
              list direct {
                // NCS patched for predictable order
                ordered-by user;
                tailf:cli-drop-node-name;
                tailf:cli-suppress-mode;
                key "name";
                leaf name {
                  type string;
                }
                leaf auth-port {
                  type string;
                }
                leaf acct-port {
                  type string;
                }
              }
            }
            container ip {
              container radius {
                leaf source-interface {
                  type string;
                }
              }
              container vrf {
                leaf forwarding {
                  // NCS drop tailf-common:cli-diff-dependency statement
                  // NCS drop tailf-common:cli-diff-dependency statement
                  type string;
                }
              }
            }
          }
        }
      }
      container authentication {
        // NCS drop tailf-common:cli-diff-dependency statement
        container dot1x {
          list dot1x-list {
            // NCS patched for predictable order
            ordered-by user;
            tailf:cli-suppress-mode;
            key "name";
            leaf name {
              type string;
            }
            uses ncs_template_aaa-authentication-dot1x-grouping;
          }
          container default {
            uses ncs_template_aaa-authentication-dot1x-grouping;
          }
        }
        container enable {
          container default {
            leaf enable {
              type empty;
            }
            leaf group {
              type string;
            }
            leaf line {
              type empty;
            }
            leaf none {
              type empty;
            }
          }
        }
        list login {
          // NCS patched for predictable order
          ordered-by user;
          tailf:cli-suppress-mode;
          key "name";
          leaf name {
            type string;
          }
          leaf group {
            type string;
          }
          leaf local {
            type empty;
          }
          leaf none {
            type empty;
          }
        }
        list ppp {
          // NCS patched for predictable order
          ordered-by user;
          tailf:cli-suppress-mode;
          key "id";
          leaf id {
            type string;
          }
          container a1 {
            tailf:cli-drop-node-name;
            choice auth-choice {
              leaf if-needed {
                type empty;
              }
              leaf none {
                type empty;
              }
              leaf krb5 {
                type empty;
              }
              leaf local {
                type empty;
              }
              leaf local-case {
                type empty;
              }
              leaf group {
                type string;
              }
              leaf cache {
                type string;
              }
            }
          }
          container a2 {
            // NCS drop when statement
            tailf:cli-drop-node-name;
            choice auth-choice {
              leaf group {
                type string;
              }
              leaf cache {
                type string;
              }
              leaf none {
                type empty;
              }
              leaf krb5 {
                // NCS drop when statement
                type empty;
              }
              leaf local {
                // NCS drop when statement
                type empty;
              }
              leaf local-case {
                // NCS drop when statement
                type empty;
              }
            }
          }
          container a3 {
            // NCS drop when statement
            tailf:cli-drop-node-name;
            choice auth-choice {
              leaf group {
                type string;
              }
              leaf cache {
                type string;
              }
              leaf none {
                type empty;
              }
              leaf krb5 {
                // NCS drop when statement
                type empty;
              }
              leaf local {
                // NCS drop when statement
                type empty;
              }
              leaf local-case {
                // NCS drop when statement
                type empty;
              }
            }
          }
          container a4 {
            // NCS drop when statement
            tailf:cli-drop-node-name;
            choice auth-choice {
              leaf group {
                type string;
              }
              leaf cache {
                type string;
              }
              leaf none {
                type empty;
              }
              leaf krb5 {
                // NCS drop when statement
                type empty;
              }
              leaf local {
                // NCS drop when statement
                type empty;
              }
              leaf local-case {
                // NCS drop when statement
                type empty;
              }
            }
          }
        }
      }
      container authorization {
        // NCS drop tailf-common:cli-diff-dependency statement
        list commands {
          // NCS patched for predictable order
          ordered-by user;
          tailf:cli-suppress-mode;
          key "level list-name";
          leaf level {
            type string;
          }
          leaf list-name {
            type string;
          }
          leaf group {
            type string;
          }
          leaf if-authenticated {
            type empty;
          }
          leaf local {
            type empty;
          }
          leaf none {
            type empty;
          }
        }
        leaf console {
          type empty;
        }
        leaf config-commands {
          type empty;
        }
        list exec {
          // NCS patched for predictable order
          ordered-by user;
          tailf:cli-suppress-mode;
          key "name";
          leaf name {
            type string;
          }
          leaf group {
            type string;
          }
          leaf local {
            type empty;
          }
          leaf none {
            type empty;
          }
        }
        list eventmanager {
          // NCS patched for predictable order
          ordered-by user;
          tailf:cli-suppress-mode;
          key "name";
          leaf name {
            type string;
          }
          leaf group {
            type string;
          }
          leaf local {
            type empty;
          }
          leaf none {
            type empty;
          }
        }
        list network {
          // NCS patched for predictable order
          ordered-by user;
          tailf:cli-suppress-mode;
          key "id";
          leaf id {
            type string;
          }
          container a1 {
            tailf:cli-drop-node-name;
            choice auth-choice {
              leaf if-authenticated {
                type empty;
              }
              leaf none {
                type empty;
              }
              leaf local {
                type empty;
              }
              leaf group {
                type string;
              }
              leaf cache {
                type string;
              }
            }
          }
          container a2 {
            // NCS drop when statement
            tailf:cli-drop-node-name;
            choice auth-choice {
              leaf group {
                type string;
              }
              leaf cache {
                type string;
              }
              leaf if-authenticated {
                type empty;
              }
              leaf none {
                type empty;
              }
              leaf local {
                // NCS drop when statement
                type empty;
              }
            }
          }
          container a3 {
            // NCS drop when statement
            tailf:cli-drop-node-name;
            choice auth-choice {
              leaf group {
                type string;
              }
              leaf cache {
                type string;
              }
              leaf none {
                type empty;
              }
              leaf if-authenticated {
                type empty;
              }
              leaf local {
                // NCS drop when statement
                type empty;
              }
            }
          }
          container a4 {
            // NCS drop when statement
            tailf:cli-drop-node-name;
            choice auth-choice {
              leaf group {
                type string;
              }
              leaf cache {
                type string;
              }
              leaf none {
                type empty;
              }
              leaf if-authenticated {
                type empty;
              }
              leaf local {
                // NCS drop when statement
                type empty;
              }
            }
          }
        }
      }
      container accounting {
        // NCS drop tailf-common:cli-diff-dependency statement
        list commands {
          // NCS patched for predictable order
          ordered-by user;
          tailf:cli-suppress-mode;
          key "level list-name";
          leaf level {
            type string;
          }
          leaf list-name {
            type string;
          }
          leaf action-type {
            tailf:cli-drop-node-name;
            type string;
          }
          leaf broadcast {
            type empty;
          }
          leaf group {
            type string;
          }
        }
        list exec {
          // NCS patched for predictable order
          ordered-by user;
          key "name";
          leaf name {
            type string;
          }
          choice accounting-choice {
            leaf none {
              type empty;
            }
            container start-stop {
              leaf broadcast {
                type empty;
              }
              leaf group {
                type string;
              }
            }
            container stop-only {
              leaf broadcast {
                type empty;
              }
              leaf group {
                type string;
              }
            }
          }
        }
        list network {
          // NCS patched for predictable order
          ordered-by user;
          tailf:cli-suppress-mode;
          key "id";
          leaf id {
            type string;
          }
          choice network-choice {
            case a {
              leaf none {
                type empty;
              }
            }
            case b {
              leaf mode {
                tailf:cli-drop-node-name;
                type string;
              }
              leaf broadcast {
                type empty;
              }
              container a1 {
                tailf:cli-drop-node-name;
                leaf group {
                  type string;
                }
              }
              container a2 {
                tailf:cli-drop-node-name;
                leaf group {
                  type string;
                }
              }
              container a3 {
                tailf:cli-drop-node-name;
                leaf group {
                  type string;
                }
              }
              container a4 {
                tailf:cli-drop-node-name;
                leaf group {
                  type string;
                }
              }
            }
          }
        }
      }
      leaf session-id {
        // NCS drop tailf-common:cli-diff-dependency statement
        type string;
      }
    }
    container ethernet {
      list evc {
        // NCS patched for predictable order
        ordered-by user;
        key "name";
        leaf name {
          type string;
        }
      }
      container cfm {
        leaf ieee {
          type empty;
        }
        leaf global {
          type empty;
        }
        list domain {
          // NCS patched for predictable order
          ordered-by user;
          key "name";
          leaf name {
            type string;
          }
          leaf level {
            type string;
          }
          leaf service {
            type string;
          }
          leaf evc {
            type string;
          }
          leaf vlan {
            type string;
          }
        }
      }
    }
    list alarm-contact {
      // NCS patched for predictable order
      ordered-by user;
      tailf:cli-suppress-mode;
      key "name";
      leaf name {
        type string;
      }
      leaf description {
        type string;
      }
      leaf severity {
        type string;
      }
      leaf trigger {
        type string;
      }
    }
    container access-list {
      list access-list-standard-range {
        // NCS patched for predictable order
        ordered-by user;
        tailf:cli-drop-node-name;
        tailf:cli-suppress-mode;
        key "listnumber";
        leaf listnumber {
          tailf:cli-drop-node-name;
          type string;
        }
        list std-access-list-rule {
          // NCS patched for predictable order
          ordered-by user;
          tailf:cli-suppress-mode;
          tailf:cli-drop-node-name;
          key "rule";
          leaf rule {
            tailf:cli-drop-node-name;
            type string;
          }
        }
      }
      list access-list-extended-range {
        // NCS patched for predictable order
        ordered-by user;
        tailf:cli-drop-node-name;
        tailf:cli-suppress-mode;
        key "listnumber";
        leaf listnumber {
          tailf:cli-drop-node-name;
          type string;
        }
        list ext-access-list-rule {
          // NCS patched for predictable order
          ordered-by user;
          tailf:cli-suppress-mode;
          tailf:cli-drop-node-name;
          key "rule";
          leaf rule {
            tailf:cli-drop-node-name;
            type string;
          }
        }
      }
    }
    container crypto {
      container pki {
        list trustpoint {
          // NCS patched for predictable order
          ordered-by user;
          key "id";
          leaf id {
            type string;
          }
          container enrollment {
            leaf http-proxy {
              type string;
            }
            container mode {
              leaf ra {
                type empty;
              }
            }
            leaf profile {
              type string;
            }
            container retry {
              leaf count {
                type string;
              }
              leaf period {
                type string;
              }
            }
            leaf selfsigned {
              type empty;
            }
            container terminal {
              presence "true";
              leaf pem {
                type empty;
              }
            }
            leaf url {
              type string;
            }
          }
          leaf revocation-check {
            type string;
          }
          leaf rsakeypair {
            type string;
          }
          leaf subject-name {
            type string;
          }
        }
        container certificate {
          list chain {
            // NCS patched for predictable order
            ordered-by user;
            key "name";
            leaf name {
              type string;
            }
            list certificate {
              // NCS patched for predictable order
              ordered-by user;
              tailf:cli-suppress-mode;
              key "serial";
              leaf serial {
                type string;
              }
              leaf certtype {
                tailf:cli-drop-node-name;
                type string;
              }
              leaf cert {
                tailf:cli-drop-node-name;
                type string;
              }
            }
          }
        }
        container token {
          list token-name {
            // NCS patched for predictable order
            ordered-by user;
            tailf:cli-suppress-mode;
            tailf:cli-drop-node-name;
            key "name";
            leaf name {
              type string;
            }
            uses ncs_template_crypto-pki-token-grouping;
          }
        }
        container default {
          uses ncs_template_crypto-pki-token-grouping;
        }
      }
    }
    container mpls {
      container atm {
        leaf disable-headend-vc {
          type empty;
        }
      }
      leaf cos-map {
        type string;
      }
      container ip {
        leaf default-route {
          type empty;
        }
        container conf {
          tailf:cli-drop-node-name;
          leaf propagate-ttl {
            type string;
            // NCS drop default statement
          }
        }
        container conf-arg {
          tailf:cli-drop-node-name;
          container propagate-ttl {
            leaf forwarded {
              type string;
            }
          }
        }
        container ttl-expiration {
          leaf pop {
            type string;
          }
        }
      }
      container label {
        container atm {
          leaf disable-headend-vc {
            type empty;
          }
        }
        leaf protocol {
          type string;
          // NCS drop default statement
        }
        container range {
          leaf min {
            tailf:cli-drop-node-name;
            type string;
          }
          leaf max {
            tailf:cli-drop-node-name;
            type string;
          }
        }
      }
      container ldp {
        container enable {
          tailf:cli-drop-node-name;
          leaf advertise-labels {
            type string;
            // NCS drop default statement
          }
        }
        container enable2 {
          tailf:cli-drop-node-name;
          container advertise-labels {
            container for {
              leaf from {
                tailf:cli-drop-node-name;
                type string;
              }
              leaf to {
                type string;
              }
            }
            container interface {
              list FastEthernet {
                // NCS patched for predictable order
                ordered-by user;
                tailf:cli-suppress-mode;
                key "name";
                leaf name {
                  type string;
                }
              }
            }
            leaf oldstyle {
              type empty;
            }
          }
        }
        container atm {
          leaf control-mode {
            type string;
            // NCS drop default statement
          }
          leaf vc-merge {
            type string;
            // NCS drop default statement
          }
        }
        container backoff {
          leaf initial {
            tailf:cli-drop-node-name;
            type string;
          }
          leaf max {
            tailf:cli-drop-node-name;
            type string;
          }
        }
        container discovery {
          container hello {
            leaf holdtime {
              type string;
            }
            leaf interval {
              type string;
            }
          }
          container targeted-hello {
            container accept {
              presence "Accept targeted hellos";
              leaf from {
                type string;
              }
            }
            leaf holdtime {
              type string;
            }
            leaf interval {
              type string;
            }
          }
        }
        container explicit-null {
          presence "Advertise Explicit Null label in place of Implicit Null";
          leaf for {
            type string;
          }
          leaf to {
            type string;
          }
        }
        container graceful-restart {
          presence "Configure Graceful Restart timers";
          container timers {
            leaf forwarding-holding {
              type string;
            }
            leaf max-recovery {
              type string;
            }
            leaf neighbor-liveness {
              type string;
            }
          }
        }
        leaf holdtime {
          type string;
        }
        container logging {
          leaf neighbor-changes {
            type empty;
          }
        }
        leaf loop-detection {
          type empty;
        }
        leaf maxhops {
          type string;
        }
        list neighbor {
          // NCS patched for predictable order
          ordered-by user;
          tailf:cli-suppress-mode;
          key "address";
          leaf address {
            type string;
          }
          leaf implicit-withdraw {
            type empty;
          }
          container lables {
            leaf accept {
              type string;
            }
          }
          container password {
            leaf enctype {
              tailf:cli-drop-node-name;
              type string;
              // NCS drop default statement
            }
            leaf text {
              tailf:cli-drop-node-name;
              type string;
            }
          }
          container targeted {
            presence "Establish targeted session";
            leaf protocol {
              tailf:cli-drop-node-name;
              type string;
            }
          }
        }
        container request-labels {
          leaf for {
            type string;
          }
        }
        container router-id {
          leaf interface {
            tailf:cli-drop-node-name;
            type string;
          }
          leaf force {
            type empty;
          }
        }
      }
      container prefix-map {
        leaf nr {
          tailf:cli-drop-node-name;
          type string;
        }
        leaf access-list {
          type string;
        }
        leaf cos-map {
          type string;
        }
      }
      container traffic-eng {
        container auto-bw {
          container timers {
            presence "Enable auto-bw Timers Collection and Application";
            leaf frequency {
              type string;
            }
          }
        }
        container link-management {
          container timers {
            leaf bandwidth-hold {
              type string;
            }
            leaf periodic-flooding {
              type string;
            }
          }
        }
        container logging {
          container lsp {
            container path-errors {
              presence "Log LSP Path Error traps";
              leaf access-list {
                tailf:cli-drop-node-name;
                type ncs_template_access-list-type;
              }
            }
            container preemption {
              presence "Log LSP Preemption traps";
              leaf access-list {
                tailf:cli-drop-node-name;
                type ncs_template_access-list-type;
              }
            }
            container reservation-errors {
              presence "Log LSP Reservation Error traps";
              leaf access-list {
                tailf:cli-drop-node-name;
                type ncs_template_access-list-type;
              }
            }
            container setups {
              presence "Log LSP Establishment Traps";
              leaf access-list {
                tailf:cli-drop-node-name;
                type ncs_template_access-list-type;
              }
            }
            container teardowns {
              presence "Log LSP Teardown Traps";
              leaf access-list {
                tailf:cli-drop-node-name;
                type ncs_template_access-list-type;
              }
            }
          }
          container tunnel {
            container lsp-selection {
              presence "Log Tunnel LSP Selection traps";
              leaf access-list {
                tailf:cli-drop-node-name;
                type ncs_template_access-list-type;
              }
            }
            container path {
              container change {
                presence "Log Tunnel Path change traps";
                leaf access-list {
                  tailf:cli-drop-node-name;
                  type ncs_template_access-list-type;
                }
              }
            }
          }
        }
        container path-selection {
          leaf metric {
            type string;
          }
          container overload {
            container allow {
              leaf head {
                type empty;
              }
              leaf middle {
                type empty;
              }
              leaf tail {
                type empty;
              }
            }
          }
        }
        container reoptimize {
          container events {
            leaf link-up {
              type empty;
            }
          }
          container timers {
            container delay {
              leaf cleanup {
                type string;
              }
              leaf installation {
                type string;
              }
            }
            leaf frequency {
              type string;
            }
          }
        }
        container signalling {
          container advertise {
            container implicit-null {
              presence "Use MPLS encoding for Implicit-Null Label in signalling messages";
              leaf nr {
                tailf:cli-drop-node-name;
                type string;
              }
            }
          }
          container forwarding {
            leaf sync {
              type empty;
            }
          }
          container restart {
            container neighbors {
              presence "Identify signalling restart capable neighbors";
              leaf nr {
                tailf:cli-drop-node-name;
                type string;
              }
            }
          }
        }
        container topology {
          container holddown {
            leaf sigerr {
              type string;
            }
          }
        }
        leaf tunnels {
          type empty;
        }
      }
    }
    container router {
      list bgp {
        // NCS patched for predictable order
        ordered-by user;
        // NCS drop tailf-common:cli-diff-dependency statement
        // NCS drop tailf-common:cli-diff-dependency statement
        key "as-no";
        // NCS drop max-elements statement
        leaf as-no {
          type string;
        }
        uses ncs_template_bgp-address-family-grouping;
        container address-family {
          container no-vrf {
            tailf:cli-drop-node-name;
            list ipv4 {
              // NCS patched for predictable order
              ordered-by user;
              key "unicast-multicast";
              leaf unicast-multicast {
                type string;
              }
              uses ncs_template_bgp-address-family-grouping;
            }
          }
          container with-vrf {
            tailf:cli-drop-node-name;
            list ipv4 {
              // NCS patched for predictable order
              ordered-by user;
              tailf:cli-suppress-mode;
              key "unicast-multicast";
              leaf unicast-multicast {
                type string;
              }
              list vrf {
                // NCS patched for predictable order
                ordered-by user;
                // NCS drop tailf-common:cli-diff-dependency statement
                // NCS drop tailf-common:cli-diff-dependency statement
                key "name";
                leaf name {
                  type string;
                }
                uses ncs_template_bgp-address-family-grouping;
              }
            }
          }
          list ipv6 {
            // NCS patched for predictable order
            ordered-by user;
            tailf:cli-suppress-mode;
            key "unicast-multicast";
            leaf unicast-multicast {
              type string;
            }
            list vrf {
              // NCS patched for predictable order
              ordered-by user;
              // NCS drop tailf-common:cli-diff-dependency statement
              key "name";
              leaf name {
                type string;
              }
              uses ncs_template_bgp-address-family-grouping;
            }
            uses ncs_template_bgp-address-family-grouping;
          }
          list vpnv4 {
            // NCS patched for predictable order
            ordered-by user;
            key "unicast-multicast";
            leaf unicast-multicast {
              type string;
            }
            uses ncs_template_bgp-address-family-grouping;
          }
          list vpnv6 {
            // NCS patched for predictable order
            ordered-by user;
            key "unicast-multicast";
            leaf unicast-multicast {
              type string;
            }
            uses ncs_template_bgp-address-family-grouping;
          }
          list nsap {
            // NCS patched for predictable order
            ordered-by user;
            key "unicast-multicast";
            leaf unicast-multicast {
              type string;
            }
            uses ncs_template_bgp-address-family-grouping;
          }
        }
        container template {
          list peer-policy {
            // NCS patched for predictable order
            ordered-by user;
            key "name";
            leaf name {
              type string;
            }
          }
          list peer-session {
            // NCS patched for predictable order
            ordered-by user;
            key "name";
            leaf name {
              type string;
            }
          }
        }
      }
      list ospfv3 {
        // NCS patched for predictable order
        ordered-by user;
        key "id";
        leaf id {
          type string;
        }
        uses ncs_template_ospf-ospfv3-common-grouping;
        container address-family {
          container ipv4 {
            container unicast {
              uses ncs_template_ospf-ospfv3-common-grouping;
              uses ncs_template_ospf-ospfv3-common-address-family-grouping;
            }
          }
          container ipv6 {
            container unicast {
              uses ncs_template_ospf-ospfv3-common-grouping;
              uses ncs_template_ospf-ospfv3-common-address-family-grouping;
            }
          }
        }
      }
      list ospf {
        // NCS patched for predictable order
        ordered-by user;
        key "id";
        leaf id {
          type string;
        }
        list vrf {
          // NCS patched for predictable order
          ordered-by user;
          // NCS drop tailf-common:cli-diff-dependency statement
          // NCS drop tailf-common:cli-diff-dependency statement
          key "name";
          leaf name {
            type string;
          }
        }
        container non-vrf {
          tailf:cli-drop-node-name;
          uses ncs_template_ospf-ospfv3-common-grouping;
          uses ncs_template_ospf-ospfv3-common-address-family-grouping;
          container capability {
            leaf capability-type {
              tailf:cli-drop-node-name;
              type string;
            }
          }
          container compatible {
            leaf rfc1583 {
              type empty;
            }
          }
          uses ncs_template_distribute-list-grouping;
          container domain-id {
            choice domain-id-choice {
              leaf ip-format {
                tailf:cli-drop-node-name;
                type string;
              }
              container ip-format-secondary {
                tailf:cli-drop-node-name;
                leaf ip {
                  tailf:cli-drop-node-name;
                  type string;
                }
                leaf secondary {
                  type empty;
                }
              }
              leaf Null {
                type empty;
              }
              container type {
                leaf type-leaf {
                  tailf:cli-drop-node-name;
                  type string;
                }
                leaf value {
                  type string;
                }
              }
            }
          }
          leaf domain-tag {
            type string;
          }
          container ignore {
            container lsa {
              leaf mospf {
                type empty;
              }
            }
          }
          leaf ispf {
            type empty;
          }
          container limit {
            container retransmissions {
              leaf non-dc {
                type ncs_template_limit-dc-non-dc-type;
              }
              leaf dc {
                type ncs_template_limit-dc-non-dc-type;
              }
            }
          }
          container local-rib-criteria {
            leaf forwarding-address {
              type empty;
            }
            leaf inter-area-summary {
              type empty;
            }
            leaf nssa-translation {
              type empty;
            }
          }
          container max-metric {
            container router-lsa {
              presence "Maximum metric in self-originated router-LSAs";
              container external-lsa {
                presence "Override external-lsa metric with max-metric value";
                leaf metric {
                  tailf:cli-drop-node-name;
                  type string;
                }
              }
              leaf include-stub {
                type empty;
              }
              container on-startup {
                presence "Set maximum metric temporarily after reboot";
                choice time-wait-for-bgp-choice {
                  leaf time {
                    tailf:cli-drop-node-name;
                    type string;
                  }
                  leaf wait-for-bgp {
                    type empty;
                  }
                }
              }
              container summary-lsa {
                presence "Override summary-lsa metric with max-metric value";
                leaf metric {
                  tailf:cli-drop-node-name;
                  type string;
                }
              }
            }
          }
          container mpls {
            container ldp {
              container autoconfig {
                presence "Configure LDP automatic configuration";
                leaf area {
                  type ncs_template_ospf-area-type;
                }
              }
              container sync {
                presence "Configure LDP-IGP Synchronization";
              }
            }
            container traffic-eng {
              leaf multicast-intact {
                type empty;
              }
              leaf area {
                type ncs_template_ospf-area-type;
              }
              container interface {
                leaf name {
                  tailf:cli-drop-node-name;
                  type string;
                }
                leaf area {
                  type string;
                }
              }
              container mesh-group-container {
                tailf:cli-drop-node-name;
                leaf mesh-group {
                  type string;
                }
                leaf interface {
                  type string;
                }
                list area {
                  // NCS patched for predictable order
                  ordered-by user;
                  tailf:cli-suppress-mode;
                  key "id";
                  leaf id {
                    type ncs_template_ospf-area-type;
                  }
                }
              }
              container router-id {
                leaf interface {
                  type string;
                }
              }
            }
          }
          list neighbor {
            // NCS patched for predictable order
            ordered-by user;
            tailf:cli-suppress-mode;
            key "ip";
            leaf ip {
              type string;
            }
            container cost-database-filter-container {
              tailf:cli-drop-node-name;
              leaf cost {
                type string;
              }
              container database-filter {
                container all {
                  leaf out {
                    type empty;
                  }
                }
              }
            }
            container poll-interval-priority-container {
              tailf:cli-drop-node-name;
              leaf poll-interval {
                type string;
              }
              leaf priority {
                type string;
              }
            }
          }
          list network {
            // NCS patched for predictable order
            ordered-by user;
            tailf:cli-suppress-mode;
            key "ip mask";
            leaf ip {
              type string;
            }
            leaf mask {
              type string;
            }
            leaf area {
              type ncs_template_ospf-area-type;
            }
          }
          container nsf {
            container cisco {
              container helper {
                presence "helper support";
                leaf disable {
                  type empty;
                }
              }
            }
            container ietf {
              container helper {
                presence "helper support";
                leaf disable {
                  type empty;
                }
                leaf strict-lsa-checking {
                  type empty;
                }
              }
            }
          }
          leaf prefix-suppression {
            type empty;
          }
          container process-min-time {
            leaf percent {
              type string;
            }
          }
          container traffic-share {
            container min {
              leaf across-interface {
                type empty;
              }
            }
          }
          leaf shutdown {
            type string;
          }
          list summary-address {
            // NCS patched for predictable order
            ordered-by user;
            tailf:cli-suppress-mode;
            key "ip wildcard";
            leaf ip {
              type string;
            }
            leaf wildcard {
              type string;
            }
            choice tag-no-advertise-choice {
              leaf tag {
                type string;
              }
              leaf not-advertise {
                type empty;
              }
            }
          }
        }
      }
      container isis {
        presence "true";
        uses ncs_template_isis-main-grouping;
      }
      container isis-container {
        tailf:cli-drop-node-name;
        list isis {
          // NCS patched for predictable order
          ordered-by user;
          key "area-tag";
          leaf area-tag {
            type string;
          }
          uses ncs_template_isis-main-grouping;
        }
      }
      container rip {
        uses ncs_template_router-rip-grouping;
        container address-family {
          container ipv4 {
            container unicast {
              uses ncs_template_router-rip-grouping;
            }
            list vrf {
              // NCS patched for predictable order
              ordered-by user;
              // NCS drop tailf-common:cli-diff-dependency statement
              // NCS drop tailf-common:cli-diff-dependency statement
              key "name";
              leaf name {
                type string;
              }
              uses ncs_template_address-family-vrf-grouping;
            }
          }
        }
        container default {
          container address-family {
            container ipv4 {
              presence "true";
              leaf unicast {
                type empty;
              }
              list vrf {
                // NCS patched for predictable order
                ordered-by user;
                tailf:cli-suppress-mode;
                // NCS drop tailf-common:cli-diff-dependency statement
                // NCS drop tailf-common:cli-diff-dependency statement
                key "name";
                leaf name {
                  type string;
                }
              }
            }
          }
          uses ncs_template_default-router-rip-grouping;
          container default-information {
            leaf originate {
              type empty;
            }
          }
          leaf default-metric {
            type empty;
          }
          uses ncs_template_distance-grouping;
          uses ncs_template_distribute-list-grouping;
          leaf flash-update-threshold {
            type empty;
          }
          leaf input-queue {
            type empty;
          }
          uses ncs_template_offset-list-grouping;
          leaf output-delay {
            type empty;
          }
          uses ncs_template_passive-interface-grouping;
          container redistribute {
            uses ncs_template_default-redistribute-grouping;
          }
          container timers {
            leaf basic {
              type empty;
            }
          }
          container traffic-share {
            container min {
              leaf across-interfaces {
                type empty;
              }
            }
          }
          leaf version {
            type empty;
          }
        }
      }
    }
    container snmp {
      container ifmib {
        container ifindex {
          leaf persist {
            type empty;
          }
        }
        container ifalias {
          leaf long {
            type empty;
          }
        }
      }
      container mib {
        container bulkstat {
          list object-list {
            // NCS patched for predictable order
            ordered-by user;
            tailf:cli-suppress-mode;
            key "name";
            leaf name {
              type string;
            }
          }
        }
        leaf persist {
          type string;
        }
      }
    }
    container snmp-server {
      list community {
        // NCS patched for predictable order
        ordered-by user;
        tailf:cli-suppress-mode;
        key "name";
        leaf name {
          type string;
        }
        leaf view {
          type string;
        }
        choice access-choice {
          leaf RO {
            type empty;
          }
          leaf RW {
            type empty;
          }
        }
        choice access-list-choice {
          case ipv6 {
            leaf ipv6 {
              type string;
            }
          }
          case ipv4 {
            leaf access-list-name {
              tailf:cli-drop-node-name;
              type ncs_template_std-acl-type;
            }
          }
        }
      }
      leaf contact {
        type string;
      }
      container enable {
        choice enable-choice {
          case informs {
            leaf informs {
              type empty;
            }
          }
          case traps {
            container traps {
              leaf aaa_server {
                type empty;
              }
              container alarms {
                presence "true";
                leaf informational {
                  type empty;
                }
              }
              container atm {
                container pvc {
                  presence "true";
                  container extension {
                    leaf down {
                      type empty;
                    }
                    leaf up {
                      type empty;
                    }
                    leaf mibversion {
                      type string;
                    }
                    container oam {
                      container failure {
                        leaf loopback {
                          type empty;
                        }
                      }
                    }
                  }
                  leaf interval {
                    type string;
                  }
                  leaf fail-interval {
                    type string;
                  }
                }
                container subif {
                  presence "true";
                  leaf interval {
                    type string;
                  }
                  leaf count {
                    type string;
                  }
                }
              }
              leaf authenticate-fail {
                type empty;
              }
              container auth-framework {
                presence "true";
                leaf sec-violation {
                  type empty;
                }
              }
              leaf bfd {
                type empty;
              }
              leaf bgp {
                type empty;
              }
              container bridge {
                presence "true";
                leaf newroot {
                  type empty;
                }
                leaf topologychange {
                  type empty;
                }
              }
              leaf bstun {
                type empty;
              }
              container bulkstat {
                presence "true";
                leaf collection {
                  type empty;
                }
                leaf transfer {
                  type empty;
                }
              }
              container call-home {
                presence "true";
                leaf message-send-fail {
                  type empty;
                }
                leaf server-fail {
                  type empty;
                }
              }
              leaf c2900 {
                type empty;
              }
              container c6kxbar {
                presence "true";
                leaf intbus-crcexcd {
                  type empty;
                }
                leaf intbus-crcrcvrd {
                  type empty;
                }
                leaf swbus {
                  type empty;
                }
              }
              leaf casa {
                type empty;
              }
              leaf ccme {
                type empty;
              }
              container cef {
                leaf resource-failure {
                  type empty;
                }
                leaf peer-state-change {
                  type empty;
                }
                leaf peer-fib-state-change {
                  type empty;
                }
                leaf inconsistency {
                  type empty;
                }
              }
              leaf cluster {
                type empty;
              }
              leaf channel {
                type empty;
              }
              leaf chassis {
                type empty;
              }
              leaf cnpd {
                type empty;
              }
              leaf config {
                type empty;
              }
              leaf copy-config {
                type empty;
              }
              leaf config-copy {
                type empty;
              }
              leaf config-ctid {
                type empty;
              }
              container cpu {
                presence "true";
                leaf threshold {
                  type empty;
                }
              }
              container csg {
                presence "true";
                leaf agent {
                  type empty;
                }
                leaf database {
                  type empty;
                }
                leaf quota-server {
                  type empty;
                }
              }
              leaf dial {
                type empty;
              }
              leaf director {
                type empty;
              }
              leaf dlsw {
                type empty;
              }
              leaf deauthenticate {
                type empty;
              }
              leaf disassociate {
                type empty;
              }
              leaf dnis {
                type empty;
              }
              leaf dot11-qos {
                type empty;
              }
              container dot1x {
                leaf auth-fail-vlan {
                  type empty;
                }
                leaf guest-vlan {
                  type empty;
                }
                leaf no-auth-fail-vlan {
                  type empty;
                }
                leaf no-guest-vlan {
                  type empty;
                }
              }
              leaf ds0-busyout {
                type empty;
              }
              leaf ds1 {
                type empty;
              }
              leaf ds1-loopback {
                type empty;
              }
              leaf ds3 {
                type empty;
              }
              container dsp {
                presence "true";
                leaf card-status {
                  type empty;
                }
                leaf oper-state {
                  type empty;
                }
              }
              leaf eigrp {
                type empty;
              }
              container energywise {
                presence "true";
                leaf event-occured {
                  type empty;
                }
                leaf level-change {
                  type empty;
                }
                leaf neighbor-added {
                  type empty;
                }
                leaf neighbor-deleted {
                  type empty;
                }
              }
              leaf entity {
                type empty;
              }
              container entity-diag {
                presence "true";
                leaf boot-up-fail {
                  type empty;
                }
                leaf hm-test-recover {
                  type empty;
                }
                leaf hm-thresh-reached {
                  type empty;
                }
                leaf scheduled-test-fail {
                  type empty;
                }
              }
              container envmon {
                presence "true";
                leaf fan {
                  type empty;
                }
                leaf shutdown {
                  type empty;
                }
                leaf supply {
                  type empty;
                }
                leaf temperature {
                  type empty;
                }
                leaf status {
                  type empty;
                }
              }
              container errdisable {
                presence "true";
                leaf notification-rate {
                  type string;
                }
              }
              leaf ether-oam {
                type empty;
              }
              container ethernet {
                container cfm {
                  leaf alarm {
                    type empty;
                  }
                  container cc {
                    presence "true";
                    leaf config {
                      type empty;
                    }
                    leaf cross-connect {
                      type empty;
                    }
                    leaf loop {
                      type empty;
                    }
                    leaf mep-down {
                      type empty;
                    }
                    leaf mep-up {
                      type empty;
                    }
                  }
                  container crosscheck {
                    presence "true";
                    leaf mep-missing {
                      type empty;
                    }
                    leaf mep-unknown {
                      type empty;
                    }
                    leaf service-up {
                      type empty;
                    }
                  }
                }
                container evc {
                  presence "true";
                  leaf create {
                    type empty;
                  }
                  leaf delete {
                    type empty;
                  }
                  leaf status {
                    type empty;
                  }
                }
              }
              leaf event-manager {
                type empty;
              }
              container firewall {
                presence "true";
                leaf serverstatus {
                  type empty;
                }
              }
              container flash {
                presence "true";
                leaf insertion {
                  type empty;
                }
                leaf removal {
                  type empty;
                }
              }
              leaf flowmon {
                type empty;
              }
              container flex-links {
                presence "true";
                leaf status {
                  type empty;
                }
              }
              container frame-relay {
                presence "true";
                container multilink {
                  leaf bundle-mismatch {
                    type empty;
                  }
                }
                container subif {
                  presence "true";
                }
              }
              leaf fru-ctrl {
                type empty;
              }
              leaf gatekeeper {
                type empty;
              }
              leaf hsrp {
                type empty;
              }
              leaf icsudsu {
                type empty;
              }
              leaf ima {
                type empty;
              }
              leaf ipmobile {
                type empty;
              }
              leaf ipmulticast {
                type empty;
              }
              container ipsec {
                container cryptomap {
                  leaf add {
                    type empty;
                  }
                  leaf attach {
                    type empty;
                  }
                  leaf delete {
                    type empty;
                  }
                  leaf detach {
                    type empty;
                  }
                }
                container tunnel {
                  leaf start {
                    type empty;
                  }
                  leaf stop {
                    type empty;
                  }
                }
                leaf too-many-sas {
                  type empty;
                }
              }
              container isakmp {
                container policy {
                  leaf add {
                    type empty;
                  }
                  leaf delete {
                    type empty;
                  }
                }
                container tunnel {
                  leaf start {
                    type empty;
                  }
                  leaf stop {
                    type empty;
                  }
                }
              }
              container isdn {
                presence "true";
                leaf call-information {
                  type empty;
                }
                leaf chan-not-avail {
                  type empty;
                }
                leaf ietf {
                  type empty;
                }
                leaf layer2 {
                  type empty;
                }
              }
              leaf ipsla {
                type empty;
              }
              leaf isis {
                type empty;
              }
              container l2tc {
                presence "true";
                leaf sys-threshold {
                  type empty;
                }
                leaf threshold {
                  type empty;
                }
              }
              container l2tun {
                leaf session {
                  type empty;
                }
                container pseudowire {
                  leaf status {
                    type empty;
                  }
                }
              }
              leaf license {
                type empty;
              }
              container mac-notification {
                presence "true";
                container change {
                  presence "true";
                  leaf move {
                    type empty;
                  }
                  leaf threshold {
                    type empty;
                  }
                }
              }
              container mac-notification2 {
                tailf:alt-name "MAC-Notification";
                presence "true";
                leaf move {
                  type empty;
                }
                leaf threshold {
                  type empty;
                }
              }
              container memory {
                leaf bufferpeak {
                  type empty;
                }
              }
              leaf module {
                type empty;
              }
              container mpls {
                presence "true";
                container traffic-eng {
                  presence "true";
                }
                container fast-reroute {
                  presence "true";
                  leaf protected {
                    type empty;
                  }
                }
                container rfc {
                  presence "true";
                  leaf ldp {
                    type empty;
                  }
                }
                container ldp {
                  presence "true";
                  leaf pv-limit {
                    type empty;
                  }
                  leaf session-down {
                    type empty;
                  }
                  leaf session-up {
                    type empty;
                  }
                  leaf threshold {
                    type empty;
                  }
                }
                leaf vpn {
                  type empty;
                }
              }
              leaf msdp {
                type empty;
              }
              leaf mvpn {
                type empty;
              }
              container nhrp {
                presence "true";
                container nhs {
                  presence "true";
                }
                container nhc {
                  presence "true";
                }
                container nhp {
                  presence "true";
                }
                container quota-exceeded {
                  presence "true";
                }
              }
              container ospf {
                container state-change {
                  presence "true";
                  leaf if-state-change {
                    type empty;
                  }
                  leaf neighbor-state-change {
                    type empty;
                  }
                  leaf virtif-state-change {
                    type empty;
                  }
                  leaf virtneighbor-state-change {
                    type empty;
                  }
                }
                container errors {
                  presence "true";
                }
                container retransmit {
                  presence "true";
                  leaf packets {
                    type empty;
                  }
                  leaf virt-packets {
                    type empty;
                  }
                }
                container lsa {
                  presence "true";
                  leaf lsa-maxage {
                    type empty;
                  }
                  leaf lsa-originate {
                    type empty;
                  }
                }
                container cisco-specific {
                  presence "true";
                  container state-change {
                    presence "true";
                    leaf nssa-trans-change {
                      type empty;
                    }
                    container shamlink {
                      presence "true";
                      leaf interface {
                        type empty;
                      }
                      leaf interface-old {
                        type empty;
                      }
                      leaf neighbor {
                        type empty;
                      }
                    }
                  }
                  container errors {
                    presence "true";
                  }
                  container errdisable {
                    presence "true";
                    leaf notification-rate {
                      type string;
                    }
                  }
                  container retransmit {
                    presence "true";
                  }
                  container lsa {
                    presence "true";
                    leaf lsa-maxage {
                      type empty;
                    }
                    leaf lsa-originate {
                      type empty;
                    }
                  }
                }
              }
              container pim {
                presence "true";
                leaf invalid-pim-message {
                  type empty;
                }
                leaf neighbor-change {
                  type empty;
                }
                leaf rp-mapping-change {
                  type empty;
                }
              }
              container port-security {
                presence "true";
                leaf trap-rate {
                  type string;
                }
              }
              container power-ethernet {
                leaf group {
                  type string;
                }
                leaf police {
                  type empty;
                }
              }
              leaf pppoe {
                type empty;
              }
              container pw {
                presence "true";
                leaf vc {
                  type empty;
                }
              }
              leaf rep {
                type empty;
              }
              leaf resource-policy {
                type empty;
              }
              leaf rf {
                type empty;
              }
              leaf rogue-ap {
                type empty;
              }
              leaf rsvp {
                type empty;
              }
              leaf rtr {
                type empty;
              }
              container slb {
                presence "true";
                leaf csrp {
                  type empty;
                }
                leaf real {
                  type empty;
                }
                leaf virtual {
                  type empty;
                }
              }
              container snmp {
                leaf authentication {
                  type empty;
                }
                leaf coldstart {
                  type empty;
                }
                leaf linkdown {
                  type empty;
                }
                leaf linkup {
                  type empty;
                }
                leaf warmstart {
                  type empty;
                }
              }
              leaf sonet {
                type empty;
              }
              leaf srst {
                type empty;
              }
              leaf srp {
                type empty;
              }
              container stackwise {
                presence "true";
                leaf GLS {
                  type empty;
                }
                leaf ILS {
                  type empty;
                }
                leaf SRLS {
                  type empty;
                }
                leaf insufficient-power {
                  type empty;
                }
                leaf invalid-input-current {
                  type empty;
                }
                leaf invalid-output-current {
                  type empty;
                }
                leaf member-removed {
                  type empty;
                }
                leaf member-upgrade-notification {
                  type empty;
                }
                leaf new-master {
                  type empty;
                }
                leaf new-member {
                  type empty;
                }
                leaf port-change {
                  type empty;
                }
                leaf power-budget-warning {
                  type empty;
                }
                leaf power-invalid-topology {
                  type empty;
                }
                leaf power-link-status-changed {
                  type empty;
                }
                leaf power-oper-status-changed {
                  type empty;
                }
                leaf power-priority-conflict {
                  type empty;
                }
                leaf power-version-mismatch {
                  type empty;
                }
                leaf ring-redundant {
                  type empty;
                }
                leaf stack-mismatch {
                  type empty;
                }
                leaf unbalanced-power-supplies {
                  type empty;
                }
                leaf under-budget {
                  type empty;
                }
                leaf under-voltage {
                  type empty;
                }
              }
              container stpx {
                presence "true";
                leaf inconsistency {
                  type empty;
                }
                leaf root-inconsistency {
                  type empty;
                }
                leaf loop-inconsistency {
                  type empty;
                }
              }
              leaf stun {
                type empty;
              }
              leaf switch-over {
                type empty;
              }
              leaf syslog {
                type empty;
              }
              container transceiver {
                leaf all {
                  type empty;
                }
              }
              leaf tty {
                type empty;
              }
              container udld {
                presence "true";
                leaf link-fail-rpt {
                  type empty;
                }
                leaf status-change {
                  type empty;
                }
              }
              leaf vlancreate {
                type empty;
              }
              leaf vlandelete {
                type empty;
              }
              leaf vlan-mac-limit {
                type empty;
              }
              leaf vlan-membership {
                type empty;
              }
              leaf voice {
                type empty;
              }
              container vrfmib {
                leaf vrf-up {
                  type empty;
                }
                leaf vrf-down {
                  type empty;
                }
                leaf vnet-trunk-up {
                  type empty;
                }
                leaf vnet-trunk-down {
                  type empty;
                }
              }
              leaf vrrp {
                type empty;
              }
              leaf vsimaster {
                type empty;
              }
              container vstack {
                presence "true";
                leaf addition {
                  type empty;
                }
                leaf failure {
                  type empty;
                }
                leaf lost {
                  type empty;
                }
                leaf operation {
                  type empty;
                }
              }
              leaf vtp {
                type empty;
              }
              leaf wlan-wep {
                type empty;
              }
              leaf xgcp {
                type empty;
              }
            }
          }
        }
      }
      container engineID {
        leaf local {
          type string;
        }
        container remote;
      }
      list group {
        // NCS patched for predictable order
        ordered-by user;
        tailf:cli-suppress-mode;
        key "id";
        leaf id {
          type string;
        }
        choice security-model {
          container v1;
          container v2c;
          container v3 {
            leaf security-level {
              tailf:cli-drop-node-name;
              type string;
            }
            leaf context {
              type string;
            }
            leaf match {
              type string;
            }
            leaf read {
              type string;
            }
            leaf write {
              type string;
            }
            leaf notify {
              type string;
            }
            leaf access {
              type string;
            }
          }
        }
      }
      list host {
        // NCS patched for predictable order
        ordered-by user;
        tailf:cli-suppress-mode;
        key "ip-address";
        leaf ip-address {
          type ncs_template_host-type;
        }
        leaf vrf {
          // NCS drop tailf-common:cli-diff-dependency statement
          // NCS drop tailf-common:cli-diff-dependency statement
          type string;
        }
        choice informs-traps-choice {
          leaf informs {
            type empty;
          }
          leaf traps {
            type empty;
          }
          // NCS drop default statement
        }
        container version {
          leaf version {
            tailf:cli-drop-node-name;
            type string;
          }
          leaf security-level {
            tailf:cli-drop-node-name;
            // NCS drop when statement
            type string;
          }
        }
        list community-string {
          // NCS patched for predictable order
          ordered-by user;
          tailf:cli-drop-node-name;
          tailf:cli-suppress-mode;
          key "name";
          leaf name {
            type string;
          }
          leaf aaa_server {
            type empty;
          }
          leaf alarms {
            type empty;
          }
          leaf atm {
            type empty;
          }
          leaf bfd {
            type empty;
          }
          leaf bgp {
            type empty;
          }
          leaf bstun {
            type empty;
          }
          leaf bulkstat {
            type empty;
          }
          leaf call-home {
            type empty;
          }
          leaf casa {
            type empty;
          }
          leaf cef {
            type empty;
          }
          leaf cnpd {
            type empty;
          }
          leaf config {
            type empty;
          }
          leaf config-copy {
            type empty;
          }
          leaf config-ctid {
            type empty;
          }
          leaf cpu {
            type empty;
          }
          leaf dhcp {
            type empty;
          }
          leaf dlsw {
            type empty;
          }
          leaf ds1 {
            type empty;
          }
          leaf dsp {
            type empty;
          }
          leaf dspu {
            type empty;
          }
          leaf eigrp {
            type empty;
          }
          leaf entity {
            type empty;
          }
          leaf entity-diag {
            type empty;
          }
          leaf entity-qfp {
            type empty;
          }
          leaf entity-state {
            type empty;
          }
          leaf ethernet-cfm {
            type empty;
          }
          leaf evc {
            type empty;
          }
          leaf event-manager {
            type empty;
          }
          leaf firewall {
            type empty;
          }
          leaf flash {
            type empty;
          }
          leaf flowmon {
            type empty;
          }
          leaf frame-relay {
            type empty;
          }
          leaf fru-ctrl {
            type empty;
          }
          leaf gdoi {
            type empty;
          }
          leaf hsrp {
            type empty;
          }
          leaf iplocalpool {
            type empty;
          }
          leaf ipmulticast {
            type empty;
          }
          leaf ipsec {
            type empty;
          }
          leaf ipsla {
            type empty;
          }
          leaf isakmp {
            type empty;
          }
          leaf isg-mib {
            type empty;
          }
          leaf isis {
            type empty;
          }
          leaf l2tun-pseudowire-status {
            type empty;
          }
          leaf l2tun-session {
            type empty;
          }
          leaf license {
            type empty;
          }
          leaf memory {
            type empty;
          }
          leaf mpls-fast-reroute {
            type empty;
          }
          leaf mpls-ldp {
            type empty;
          }
          leaf mpls-traffic-eng {
            type empty;
          }
          leaf mpls-vpn {
            type empty;
          }
          leaf msdp {
            type empty;
          }
          leaf mvpn {
            type empty;
          }
          leaf nhrp {
            type empty;
          }
          leaf ospf {
            type empty;
          }
          leaf ospfv3 {
            type empty;
          }
          leaf pfr {
            type empty;
          }
          leaf pim {
            type empty;
          }
          leaf pw-vc {
            type empty;
          }
          leaf resource-policy {
            type empty;
          }
          leaf rf {
            type empty;
          }
          leaf rsrb {
            type empty;
          }
          leaf rsvp {
            type empty;
          }
          leaf sdlc {
            type empty;
          }
          leaf sdllc {
            type empty;
          }
          leaf snmp {
            type empty;
          }
          leaf sonet {
            type empty;
          }
          leaf srp {
            type empty;
          }
          leaf stun {
            type empty;
          }
          leaf syslog {
            type empty;
          }
          leaf trustsec-sxp {
            type empty;
          }
          leaf tty {
            type empty;
          }
          leaf udp-port {
            type empty;
          }
          leaf voice {
            type empty;
          }
          leaf vrfmib {
            type empty;
          }
          leaf vrrp {
            type empty;
          }
          leaf x25 {
            type empty;
          }
        }
      }
      container ip {
        leaf precedence {
          type string;
        }
      }
      container ifindex {
        leaf persist {
          type empty;
        }
      }
      leaf location {
        type string;
      }
      container manager {
        presence "true";
        leaf session-timeout {
          type string;
        }
      }
      leaf queue-length {
        type string;
      }
      container source-interface {
        container informs {
          // NCS drop tailf-common:cli-diff-dependency statement
          uses ncs_template_interface-grouping;
        }
        container traps {
          // NCS drop tailf-common:cli-diff-dependency statement
          uses ncs_template_interface-grouping;
        }
      }
      container trap {
        leaf timeout {
          type string;
        }
      }
      container trap-source {
        // NCS drop tailf-common:cli-diff-dependency statement
        uses ncs_template_interface-grouping;
      }
      list view {
        // NCS patched for predictable order
        ordered-by user;
        tailf:cli-suppress-mode;
        key "name mib";
        leaf name {
          type string;
        }
        leaf mib {
          type string;
        }
        leaf inc-exl {
          tailf:cli-drop-node-name;
          type string;
        }
      }
    }
    container dot11 {
      leaf syslog {
        type empty;
      }
    }
    container license {
      container udi {
        leaf pid {
          type string;
        }
        leaf sn {
          type string;
        }
      }
      container boot {
        container level {
          container ipbase {
            presence "true";
            leaf switch {
              type string;
            }
          }
          container ipservices {
            presence "true";
            leaf switch {
              type empty;
            }
          }
          container lanbase {
            presence "true";
            leaf switch {
              type empty;
            }
          }
        }
      }
    }
    list voice-card {
      // NCS patched for predictable order
      ordered-by user;
      key "slot";
      leaf slot {
        type string;
      }
    }
    container card {
      leaf type {
        type string;
      }
      leaf slot {
        tailf:cli-drop-node-name;
        type string;
      }
      leaf bay {
        tailf:cli-drop-node-name;
        type string;
      }
    }
    container event {
      container manager {
        list applet {
          // NCS patched for predictable order
          ordered-by user;
          key "name";
          leaf name {
            type string;
          }
          leaf authorization {
            type string;
          }
          leaf class {
            type string;
          }
          leaf trap {
            type empty;
          }
          container event {
            container snmp-notification {
              leaf oid {
                type string;
              }
              leaf oid-val {
                type string;
              }
              leaf op {
                type ncs_template_operator-type;
              }
              leaf src-ip-address {
                type string;
              }
              leaf dest-ip-address {
                type string;
              }
            }
            container syslog {
              leaf pattern {
                type string;
              }
            }
          }
          list action {
            // NCS patched for predictable order
            ordered-by user;
            tailf:cli-suppress-mode;
            key "name";
            leaf name {
              type string;
            }
            container if {
              leaf string-op-1 {
                tailf:cli-drop-node-name;
                type string;
              }
              leaf keyword {
                tailf:cli-drop-node-name;
                type ncs_template_operator-type;
              }
              leaf string-op-2 {
                tailf:cli-drop-node-name;
                type string;
              }
              leaf goto {
                type string;
              }
            }
            container info {
              container type {
                container snmp {
                  container var {
                    leaf variable-name {
                      tailf:cli-drop-node-name;
                      type string;
                    }
                    leaf oid {
                      type string;
                    }
                    leaf oid-type {
                      tailf:cli-drop-node-name;
                      type string;
                    }
                    leaf oid-type-value {
                      tailf:cli-drop-node-name;
                      type string;
                    }
                  }
                  container trap {
                    leaf enterprise-oid {
                      type string;
                    }
                    leaf generic-trapnum {
                      type string;
                    }
                    leaf specific-trapnum {
                      type string;
                    }
                    leaf trap-oid {
                      type string;
                    }
                    leaf trap-var {
                      type string;
                    }
                  }
                }
              }
            }
            leaf end {
              type empty;
            }
            container regexp {
              leaf string-pattern {
                tailf:cli-drop-node-name;
                type string;
              }
              leaf string-input {
                tailf:cli-drop-node-name;
                type string;
              }
              leaf string-match {
                tailf:cli-drop-node-name;
                type string;
              }
              leaf string-submatch1 {
                tailf:cli-drop-node-name;
                type string;
              }
              leaf string-submatch2 {
                tailf:cli-drop-node-name;
                type string;
              }
              leaf string-submatch3 {
                tailf:cli-drop-node-name;
                type string;
              }
            }
            container snmp-trap {
              presence "true";
              leaf intdata1 {
                type string;
              }
              leaf intdata2 {
                type string;
              }
              leaf strdata {
                type string;
              }
            }
            container string {
              leaf trim {
                type string;
              }
            }
            container syslog {
              leaf facility {
                type string;
              }
              leaf msg {
                type string;
              }
              leaf priority {
                type ncs_template_logging-level-type;
              }
            }
          }
          leaf description {
            type string;
          }
          container trigger;
        }
      }
    }
    leaf disable-eadi {
      type empty;
    }
    container memory-size {
      leaf iomem {
        type string;
      }
    }
    container transceiver {
      container type {
        container all {
          container monitoring {
            presence "true";
            leaf interval {
              type string;
            }
          }
        }
      }
    }
  }
  augment "/ncs:compliance/ncs:template/ncs:ned-id/ncs:config" {
    leaf version {
      type string;
    }
    container service {
      container pad {
        presence "true";
        leaf cmns {
          type empty;
        }
        leaf from-xot {
          type empty;
        }
        leaf to-xot {
          type empty;
        }
      }
      leaf password-encryption {
        type empty;
      }
      container timestamps {
        presence "true";
        container debug {
          container datetime {
            presence "true";
            leaf localtime {
              type empty;
            }
            leaf msec {
              type empty;
            }
            leaf show-timezone {
              type empty;
            }
            leaf year {
              type empty;
            }
          }
          leaf uptime {
            type empty;
          }
        }
        container log {
          container datetime {
            presence "true";
            leaf localtime {
              type empty;
            }
            leaf msec {
              type empty;
            }
            leaf show-timezone {
              type empty;
            }
            leaf year {
              type empty;
            }
          }
          leaf uptime {
            type empty;
          }
        }
      }
      container alignment {
        leaf detection {
          type empty;
        }
        leaf logging {
          type empty;
        }
      }
      leaf call-home {
        type empty;
      }
      leaf compress-config {
        type empty;
      }
      leaf config {
        type empty;
      }
      container counters {
        container max {
          leaf age {
            type string;
          }
        }
      }
      leaf dhcp {
        type empty;
      }
      leaf disable-ip-fast-frag {
        type empty;
      }
      leaf exec-callback {
        type empty;
      }
      leaf exec-wait {
        type empty;
      }
      leaf finger {
        type empty;
      }
      container heartbeat {
        leaf fatal-count {
          type string;
        }
        leaf interrupt-interval {
          type string;
        }
        leaf interrupt-max {
          type string;
        }
        leaf transmit-interval {
          type string;
        }
        leaf warning-timeout {
          type string;
        }
      }
      leaf hide-telnet-addresses {
        type empty;
      }
      leaf linenumber {
        type empty;
      }
      leaf nagle {
        type empty;
      }
      leaf old-slip-prompts {
        type empty;
      }
      leaf pt-vty-logging {
        type empty;
      }
      leaf sequence-numbers {
        type empty;
      }
      leaf slave-log {
        type empty;
      }
      leaf tcp-keepalives-in {
        type empty;
      }
      leaf tcp-keepalives-out {
        type empty;
      }
      leaf unsupported-transceiver {
        type empty;
      }
    }
    container platform {
      leaf atm-cdvt {
        type string;
      }
      container bfd {
        leaf disable-offload {
          type empty;
        }
        leaf allow-svi {
          type empty;
        }
        leaf enable-offload {
          type empty;
        }
      }
      container console {
        presence "true";
        leaf output {
          tailf:cli-drop-node-name;
          type string;
        }
      }
      container hardware {
        container throughput {
          choice throughput-choice {
            leaf disable {
              type string;
            }
            container level {
              leaf kbps {
                tailf:cli-drop-node-name;
                type string;
              }
              leaf eval-only {
                type empty;
              }
            }
          }
        }
      }
      container ipsec {
        leaf fips-mode {
          type empty;
        }
        leaf gdoi {
          type string;
        }
        container llq {
          leaf qos-group {
            type string;
          }
        }
        container reassemble {
          leaf transit {
            type empty;
          }
        }
      }
      container multicast {
        container mgre {
          leaf injection {
            type empty;
          }
        }
        container oce {
          container flag {
            leaf suppress {
              type empty;
            }
          }
        }
      }
      container punt-keepalive {
        leaf disable-kernel-core {
          type string;
        }
        container settings {
          leaf fatal-count {
            type string;
          }
          leaf transmit-interval {
            type string;
          }
          leaf warning-count {
            type string;
          }
        }
      }
      container punt-policer {
        leaf cause {
          tailf:cli-drop-node-name;
          type string;
        }
        leaf max-rate {
          tailf:cli-drop-node-name;
          type string;
        }
        leaf high {
          type empty;
        }
      }
      container qos {
        leaf marker-statistics {
          type empty;
        }
        container match-statistics {
          leaf per-filter {
            type empty;
          }
        }
        leaf performance-monitor {
          type empty;
        }
      }
      container reload {
        leaf immediate {
          type empty;
        }
      }
      leaf shell {
        type string;
      }
    }
    leaf hostname {
      type string;
    }
    container enable {
      container password {
        uses ncs_compliance_template_password-07-grouping;
      }
      leaf last-resort {
        type string;
      }
      container secret {
        leaf level {
          type string;
        }
        leaf type {
          tailf:cli-drop-node-name;
          type string;
        }
        leaf secret {
          tailf:cli-drop-node-name;
          type string;
        }
      }
      leaf use-tacacs {
        type empty;
      }
    }
    container archive {
      container log {
        container config {
          leaf hidekeys {
            type empty;
          }
        }
      }
    }
    list username {
      // NCS patched for predictable order
      ordered-by user;
      tailf:cli-suppress-mode;
      key "name";
      leaf name {
        type string;
      }
      container password {
        leaf encryption {
          tailf:cli-drop-node-name;
          type string;
        }
        leaf password {
          tailf:cli-drop-node-name;
          type string;
        }
      }
      leaf privilege {
        type string;
      }
      container secret {
        leaf encryption {
          tailf:cli-drop-node-name;
          type string;
        }
        leaf secret {
          tailf:cli-drop-node-name;
          type string;
        }
      }
    }
    list controller {
      // NCS patched for predictable order
      ordered-by user;
      key "name number";
      leaf name {
        type string;
      }
      leaf number {
        type string;
      }
      leaf framing {
        type string;
      }
      container clock {
        container source {
          choice source-choice {
            container line {
              presence "true";
              leaf line-mode {
                tailf:cli-drop-node-name;
                type string;
              }
            }
            leaf internal {
              type empty;
            }
            leaf loop-timed {
              type empty;
            }
          }
        }
      }
      leaf linecode {
        type string;
      }
      container cablelength {
        choice cablelength-choice {
          leaf long {
            type string;
          }
          leaf short {
            type string;
          }
        }
      }
      list channel-group {
        // NCS patched for predictable order
        ordered-by user;
        tailf:cli-suppress-mode;
        key "number";
        leaf number {
          type string;
        }
        leaf-list timeslots {
          // NCS patched for predictable order
          ordered-by user;
          tailf:cli-range-list-syntax;
          type string;
        }
      }
    }
    container vrf {
      list definition {
        // NCS patched for predictable order
        ordered-by user;
        key "name";
        leaf name {
          type string;
        }
        leaf description {
          type string;
        }
        leaf rd {
          type string;
        }
        container address-family {
          container ipv4 {
            presence "true";
            container export {
              leaf map {
                type string;
              }
            }
            container mdt {
              container default {
                leaf address {
                  tailf:cli-drop-node-name;
                  type string;
                }
                container mpls {
                  leaf mldp {
                    type string;
                  }
                }
              }
              container data {
                list multicast {
                  // NCS patched for predictable order
                  ordered-by user;
                  tailf:cli-drop-node-name;
                  tailf:cli-suppress-mode;
                  key "address wildcard";
                  leaf address {
                    type string;
                  }
                  leaf wildcard {
                    type string;
                  }
                }
                leaf list {
                  type ncs_compliance_template_ext-acl-type;
                }
                leaf threshold {
                  type string;
                }
              }
              leaf log-reuse {
                type empty;
              }
              leaf-list preference {
                // NCS patched for predictable order
                ordered-by user;
                type string;
              }
            }
            container route-target {
              uses ncs_compliance_template_vrf-route-target-grouping;
            }
          }
          container ipv6 {
            presence "true";
            container route-target {
              uses ncs_compliance_template_vrf-route-target-grouping;
            }
          }
        }
        container route-target {
          uses ncs_compliance_template_vrf-route-target-grouping;
        }
      }
    }
    container ip {
      leaf subnet-zero {
        type empty;
      }
      list vrf {
        // NCS patched for predictable order
        ordered-by user;
        key "name";
        leaf name {
          type string;
        }
        container bgp {
          container next-hop {
            leaf Loopback {
              type string;
            }
          }
        }
        leaf context {
          type string;
        }
        leaf description {
          type string;
        }
        container export {
          leaf map {
            type string;
          }
        }
        container import {
          choice import-choice {
            leaf map {
              type string;
            }
            container ipv4 {
              leaf ipv4-type {
                tailf:cli-drop-node-name;
                type string;
              }
              leaf upper-limit {
                tailf:cli-drop-node-name;
                type string;
              }
              leaf map {
                type string;
              }
            }
          }
        }
        container maximum {
          presence "Maximum number of routes allowed in this routing table";
          leaf routes {
            type string;
          }
          choice maximum-choice {
            // NCS drop mandatory statement
            case threshold-case {
              leaf threshold {
                tailf:cli-drop-node-name;
                type string;
              }
              leaf reinstall {
                type string;
              }
            }
            case warning-case {
              leaf warning-only {
                type empty;
              }
            }
          }
        }
        container mdt {
          presence "Backbone Multicast Distribution Tree";
          leaf default {
            type string;
          }
          leaf log-reuse {
            type empty;
          }
          container data {
            leaf mulicast-address {
              tailf:cli-drop-node-name;
              type string;
            }
            leaf wildcard-bits {
              tailf:cli-drop-node-name;
              type string;
            }
            choice mdt-data-choice {
              case mdt-data-threshold {
                leaf threshold {
                  type string;
                }
                leaf threshold-list {
                  tailf:alt-name "list";
                  type ncs_compliance_template_mdt-data-list-type;
                }
              }
              case mdt-data-list {
                leaf list {
                  type ncs_compliance_template_mdt-data-list-type;
                }
              }
            }
          }
        }
        leaf rd {
          type ncs_compliance_template_rd-type;
        }
        list route-target {
          // NCS patched for predictable order
          ordered-by user;
          tailf:cli-suppress-mode;
          key "direction target";
          leaf direction {
            type string;
          }
          leaf target {
            type ncs_compliance_template_rd-type;
          }
        }
        container vpn {
          leaf id {
            type ncs_compliance_template_vpn-id-type;
          }
        }
      }
      container mcr-conf {
        tailf:cli-drop-node-name;
        leaf multicast-routing {
          type empty;
        }
      }
      container multicast-routing {
        // NCS drop tailf-common:cli-diff-dependency statement
        // NCS drop tailf-common:cli-diff-dependency statement
        // NCS drop tailf-common:cli-diff-dependency statement
        list vrf {
          // NCS patched for predictable order
          ordered-by user;
          tailf:cli-suppress-mode;
          // NCS drop tailf-common:cli-diff-dependency statement
          key "name";
          leaf name {
            type string;
          }
          leaf distributed {
            type empty;
          }
        }
        leaf distributed {
          type empty;
        }
      }
      container as-path {
        list access-list {
          // NCS patched for predictable order
          ordered-by user;
          tailf:cli-suppress-mode;
          key "name";
          leaf name {
            type string;
          }
          list as-path-rule {
            // NCS patched for predictable order
            ordered-by user;
            tailf:cli-suppress-mode;
            tailf:cli-drop-node-name;
            key "operation rule";
            leaf operation {
              tailf:cli-drop-node-name;
              type string;
            }
            leaf rule {
              tailf:cli-drop-node-name;
              type string;
            }
          }
        }
      }
      container local {
        list pool {
          // NCS patched for predictable order
          ordered-by user;
          tailf:cli-suppress-mode;
          key "id";
          leaf id {
            type string;
          }
          leaf start {
            tailf:cli-drop-node-name;
            type string;
          }
          leaf last {
            tailf:cli-drop-node-name;
            type string;
          }
          leaf group {
            type string;
          }
        }
      }
      container cef {
        presence "true";
        leaf distributed {
          type empty;
        }
      }
      leaf classless {
        type empty;
      }
      container community-list {
        list number-standard {
          // NCS patched for predictable order
          ordered-by user;
          tailf:cli-drop-node-name;
          tailf:cli-suppress-mode;
          key "no";
          leaf no {
            type string;
          }
          uses ncs_compliance_template_ip-community-list-standard-grouping;
        }
        list number-expanded {
          // NCS patched for predictable order
          ordered-by user;
          tailf:cli-drop-node-name;
          tailf:cli-suppress-mode;
          key "no";
          leaf no {
            type string;
          }
          uses ncs_compliance_template_ip-community-list-expanded-grouping;
        }
        list expanded {
          // NCS patched for predictable order
          ordered-by user;
          tailf:cli-suppress-mode;
          key "name";
          leaf name {
            type string;
          }
          uses ncs_compliance_template_ip-community-list-expanded-grouping;
        }
        list standard {
          // NCS patched for predictable order
          ordered-by user;
          tailf:cli-suppress-mode;
          key "name";
          leaf name {
            type string;
          }
          uses ncs_compliance_template_ip-community-list-standard-grouping;
        }
      }
      container domain {
        leaf list {
          type string;
        }
        leaf lookup {
          type string;
          // NCS drop default statement
        }
        container lookup-settings {
          tailf:cli-drop-node-name;
          container lookup {
            leaf nsap {
              type empty;
            }
            container source-interface {
              // NCS drop tailf-common:cli-diff-dependency statement
              uses ncs_compliance_template_interface-grouping;
            }
          }
          leaf name {
            type string;
          }
        }
        leaf name {
          type string;
        }
      }
      container domain-lookup {
        presence "true";
        leaf nsap {
          type empty;
        }
        container source-interface {
          // NCS drop tailf-common:cli-diff-dependency statement
          uses ncs_compliance_template_interface-grouping;
        }
      }
      leaf domain-name {
        type string;
      }
      container dns {
        container server {
          presence "true";
        }
      }
      leaf default-gateway {
        type string;
      }
      container dhcp {
        list class {
          // NCS patched for predictable order
          ordered-by user;
          key "id";
          leaf id {
            type string;
          }
          container relay {
            container agent {
              leaf information {
                type empty;
              }
            }
          }
          leaf remark {
            type string;
          }
        }
        list pool {
          // NCS patched for predictable order
          ordered-by user;
          key "id";
          leaf id {
            type string;
          }
        }
        leaf smart-relay {
          type empty;
        }
        container snooping {
          presence "true";
          container information {
            container option {
              presence "true";
              leaf allow-untrusted {
                type empty;
              }
              container format {
                container remote-id {
                  choice remote-id-choice {
                    leaf hostname {
                      type empty;
                    }
                    leaf string {
                      type string;
                    }
                  }
                }
              }
            }
          }
          container track {
            leaf host {
              type empty;
            }
          }
          container verify {
            leaf mac-address {
              type empty;
            }
            leaf no-relay-agent-address {
              type empty;
            }
          }
          leaf-list vlan {
            // NCS patched for predictable order
            ordered-by user;
            type string;
          }
        }
      }
      container flow-cache {
        container timeout {
          leaf active {
            type string;
          }
        }
      }
      container flow-export {
        container destination {
          leaf ip {
            tailf:cli-drop-node-name;
            type ncs_compliance_template_host-type;
          }
          leaf port {
            tailf:cli-drop-node-name;
            type string;
          }
        }
        container source {
          // NCS drop tailf-common:cli-diff-dependency statement
          uses ncs_compliance_template_interface-grouping;
        }
        leaf version {
          type string;
        }
      }
      container forward-protocol {
        choice protocol-choice {
          leaf protocol {
            tailf:cli-drop-node-name;
            type string;
          }
          container spanning-tree {
            presence "true";
            leaf any-local-broadcast {
              type empty;
            }
          }
          leaf udp {
            type string;
          }
        }
      }
      container ftp {
        container source-interface {
          // NCS drop tailf-common:cli-diff-dependency statement
          uses ncs_compliance_template_interface-grouping;
        }
        leaf passive {
          type empty;
        }
        container password {
          uses ncs_compliance_template_password-grouping;
        }
        leaf username {
          type string;
        }
      }
      container telnet {
        leaf source-interface {
          type string;
        }
      }
      container http {
        leaf access-class {
          type string;
        }
        container authentication {
          choice authentication-choice {
            leaf aaa {
              type empty;
            }
            leaf local {
              type empty;
            }
          }
        }
        leaf server {
          type string;
        }
        leaf secure-server {
          type string;
          // NCS drop default statement
        }
        container timeout-policy {
          leaf idle {
            type string;
          }
          leaf life {
            type string;
          }
          leaf requests {
            type string;
          }
        }
        container client {
          leaf source-interface {
            type string;
          }
        }
      }
      container igmp {
        container snooping {
          presence "true";
          leaf l2-entry-limit {
            type string;
          }
        }
      }
      container multicast {
        leaf multipath {
          type empty;
        }
      }
      container nat {
        // NCS drop tailf-common:cli-diff-dependency statement
        // NCS drop tailf-common:cli-diff-dependency statement
        // NCS drop tailf-common:cli-diff-dependency statement
        list pool {
          // NCS patched for predictable order
          ordered-by user;
          tailf:cli-suppress-mode;
          key "id";
          leaf id {
            type string;
          }
          leaf start-address {
            tailf:cli-drop-node-name;
            type string;
          }
          leaf end-address {
            tailf:cli-drop-node-name;
            // NCS drop when statement
            type string;
          }
          choice prefix-choice {
            leaf netmask {
              type string;
            }
            leaf prefix-length {
              type string;
            }
          }
          leaf accounting {
            type string;
          }
          choice nat-choice {
            leaf arp-ping {
              type empty;
            }
            leaf type {
              type string;
            }
            leaf add-route {
              type empty;
            }
          }
        }
        container inside {
          container source {
            list list {
              // NCS patched for predictable order
              ordered-by user;
              tailf:cli-suppress-mode;
              key "id";
              leaf id {
                type string;
              }
              choice pool-or-interface {
                case pool-choice {
                  leaf pool {
                    type string;
                  }
                  leaf redundancy {
                    type string;
                  }
                  leaf mapping-id {
                    type string;
                  }
                }
                case interface-choice {
                  container interface {
                    uses ncs_compliance_template_interface-grouping;
                  }
                }
              }
              leaf no-payload {
                type empty;
              }
              leaf reversible {
                type empty;
              }
              leaf vrf {
                type string;
              }
              leaf match-in-vrf {
                // NCS drop when statement
                type empty;
              }
              leaf overload {
                type empty;
              }
              leaf oer {
                type empty;
              }
            }
            container static {
              list nat-static-transport-list {
                // NCS patched for predictable order
                ordered-by user;
                tailf:cli-drop-node-name;
                tailf:cli-suppress-mode;
                key "proto local-ip local-port global-ip global-port";
                leaf proto {
                  type string;
                }
                leaf local-ip {
                  tailf:cli-drop-node-name;
                  type string;
                }
                leaf local-port {
                  tailf:cli-drop-node-name;
                  type string;
                }
                leaf global-ip {
                  tailf:cli-drop-node-name;
                  type string;
                }
                leaf global-port {
                  tailf:cli-drop-node-name;
                  type string;
                }
                leaf extendable {
                  type empty;
                }
                leaf no-alias {
                  type empty;
                }
                leaf no-payload {
                  type empty;
                }
                leaf route-map {
                  type string;
                }
                leaf reversible {
                  // NCS drop when statement
                  type empty;
                }
                leaf redundancy {
                  type string;
                }
                leaf mapping-id {
                  // NCS drop when statement
                  type string;
                }
                leaf vrf {
                  type string;
                }
                leaf match-in-vrf {
                  // NCS drop when statement
                  type empty;
                }
                leaf forced {
                  type empty;
                }
                leaf overload {
                  type empty;
                }
              }
              list nat-static-transport-interface-list {
                // NCS patched for predictable order
                ordered-by user;
                tailf:cli-drop-node-name;
                tailf:cli-suppress-mode;
                key "proto local-ip local-port";
                leaf proto {
                  type string;
                }
                leaf local-ip {
                  tailf:cli-drop-node-name;
                  type string;
                }
                leaf local-port {
                  tailf:cli-drop-node-name;
                  type string;
                }
                container interface {
                  uses ncs_compliance_template_interface-grouping;
                }
                leaf global-port {
                  tailf:cli-drop-node-name;
                  type string;
                }
              }
            }
          }
          container destination {
            list list {
              // NCS patched for predictable order
              ordered-by user;
              tailf:cli-suppress-mode;
              key "id";
              leaf id {
                type string;
              }
              leaf pool {
                type string;
              }
              leaf redundancy {
                type string;
              }
              leaf mapping-id {
                type string;
              }
            }
          }
        }
        container outside {
          list list {
            // NCS patched for predictable order
            ordered-by user;
            tailf:cli-suppress-mode;
            key "id";
            leaf id {
              type string;
            }
            leaf pool {
              type string;
            }
            leaf mapping-id {
              type string;
            }
            leaf vrf {
              type string;
            }
            leaf add-route {
              type empty;
            }
          }
          list route-map {
            // NCS patched for predictable order
            ordered-by user;
            tailf:cli-suppress-mode;
            key "id";
            leaf id {
              type string;
            }
            leaf pool {
              type string;
            }
            leaf mapping-id {
              type string;
            }
            leaf vrf {
              type string;
            }
            leaf add-route {
              type empty;
            }
          }
        }
      }
      leaf-list name-server {
        // NCS patched for predictable order
        ordered-by user;
        type string;
      }
      container pim {
        // NCS drop tailf-common:cli-diff-dependency statement
        // NCS drop tailf-common:cli-diff-dependency statement
        // NCS drop tailf-common:cli-diff-dependency statement
        container ssm {
          leaf range {
            type string;
          }
        }
        list vrf {
          // NCS patched for predictable order
          ordered-by user;
          tailf:cli-suppress-mode;
          key "id";
          leaf id {
            type string;
          }
          container rp-address {
            leaf address {
              tailf:cli-drop-node-name;
              type string;
            }
            leaf access-list {
              tailf:cli-drop-node-name;
              type string;
            }
            leaf override {
              type empty;
            }
          }
        }
      }
      container prefix-list {
        list prefixes {
          // NCS patched for predictable order
          ordered-by user;
          tailf:cli-drop-node-name;
          tailf:cli-suppress-mode;
          key "name";
          leaf name {
            type string;
          }
          leaf description {
            type string;
          }
          leaf permit {
            type ios:ncs_compliance_template_ipv4-prefix;
          }
          list seq {
            // NCS patched for predictable order
            ordered-by user;
            tailf:cli-suppress-mode;
            key "no";
            leaf no {
              type string;
            }
            container deny {
              leaf ip {
                tailf:cli-drop-node-name;
                type ios:ncs_compliance_template_ipv4-prefix;
              }
              leaf ge {
                type string;
              }
              leaf le {
                type string;
              }
            }
            container permit {
              leaf ip {
                tailf:cli-drop-node-name;
                type ios:ncs_compliance_template_ipv4-prefix;
              }
              leaf ge {
                type string;
              }
              leaf le {
                type string;
              }
            }
          }
        }
        leaf sequence-number {
          type empty;
        }
      }
      container route {
        uses ncs_compliance_template_ip-route-grouping;
        leaf profile {
          type empty;
        }
        container static {
          leaf adjust-time {
            type string;
          }
          leaf inter-vrf {
            type empty;
          }
        }
        list vrf {
          // NCS patched for predictable order
          ordered-by user;
          tailf:cli-suppress-mode;
          // NCS drop tailf-common:cli-diff-dependency statement
          // NCS drop tailf-common:cli-diff-dependency statement
          // NCS drop tailf-common:cli-diff-dependency statement
          key "name";
          leaf name {
            type string;
          }
          uses ncs_compliance_template_ip-route-grouping;
        }
      }
      leaf routing {
        type empty;
      }
      container scp {
        container server {
          leaf enable {
            type empty;
          }
        }
      }
      container sla {
        container enable {
          leaf reaction-alerts {
            type empty;
          }
        }
        leaf responder {
          type empty;
        }
      }
      container bootp {
        leaf server {
          type string;
          // NCS drop default statement
        }
      }
      leaf source-route {
        type string;
        // NCS drop default statement
      }
      container ssh {
        leaf authentication-retries {
          type string;
        }
        leaf dscp {
          type string;
        }
        container logging {
          leaf events {
            type empty;
          }
        }
        leaf precedence {
          type string;
        }
        leaf time-out {
          type string;
        }
        leaf version {
          type string;
        }
      }
      container tacacs {
        container source-interface {
          // NCS drop tailf-common:cli-diff-dependency statement
          uses ncs_compliance_template_interface-grouping;
        }
      }
      container tcp {
        container path-mtu-discovery {
          presence "true";
          leaf age-timer {
            type string;
          }
        }
      }
      container tftp {
        container boot-interface {
          // NCS drop tailf-common:cli-diff-dependency statement
          uses ncs_compliance_template_interface-grouping;
        }
        container source-interface {
          // NCS drop tailf-common:cli-diff-dependency statement
          uses ncs_compliance_template_interface-grouping;
        }
      }
      container access-list {
        container standard {
          list std-named-acl {
            // NCS patched for predictable order
            ordered-by user;
            tailf:cli-drop-node-name;
            key "name";
            leaf name {
              type ncs_compliance_template_std-acl-type;
            }
            list std-access-list-rule {
              // NCS patched for predictable order
              ordered-by user;
              tailf:cli-suppress-mode;
              tailf:cli-drop-node-name;
              key "rule";
              leaf rule {
                tailf:cli-drop-node-name;
                type string;
              }
            }
          }
        }
        container extended {
          list ext-named-acl {
            // NCS patched for predictable order
            ordered-by user;
            tailf:cli-drop-node-name;
            key "name";
            leaf name {
              type string;
            }
            list ext-access-list-rule {
              // NCS patched for predictable order
              ordered-by user;
              tailf:cli-suppress-mode;
              tailf:cli-drop-node-name;
              key "rule";
              leaf rule {
                tailf:cli-drop-node-name;
                type string;
              }
            }
          }
        }
      }
    }
    container vmps {
      leaf reconfirm {
        type string;
      }
      leaf retry {
        type string;
      }
      list server {
        // NCS patched for predictable order
        ordered-by user;
        tailf:cli-suppress-mode;
        key "name";
        leaf name {
          type ncs_compliance_template_host-type;
        }
        leaf primary {
          type empty;
        }
      }
    }
    container ipv6 {
      container access-list {
        list named-acl {
          // NCS patched for predictable order
          ordered-by user;
          tailf:cli-drop-node-name;
          key "name";
          leaf name {
            type string;
          }
          list access-list-rule {
            // NCS patched for predictable order
            ordered-by user;
            tailf:cli-suppress-mode;
            tailf:cli-drop-node-name;
            key "rule";
            leaf rule {
              tailf:cli-drop-node-name;
              type string;
            }
          }
        }
      }
      leaf unicast-routing {
        type empty;
      }
      container multicast {
        container rpf {
          container backoff {
            leaf initial-delay {
              tailf:cli-drop-node-name;
              type string;
            }
            leaf max-delay {
              tailf:cli-drop-node-name;
              type string;
            }
          }
          leaf use-bgp {
            type empty;
          }
        }
      }
      container cef {
        presence "true";
        container accounting {
          leaf per-prefix {
            type empty;
          }
          leaf prefix-length {
            type empty;
          }
        }
        leaf distributed {
          type empty;
        }
      }
      container route {
        uses ncs_compliance_template_ipv6-route-grouping;
        list vrf {
          // NCS patched for predictable order
          ordered-by user;
          tailf:cli-suppress-mode;
          // NCS drop tailf-common:cli-diff-dependency statement
          // NCS drop tailf-common:cli-diff-dependency statement
          key "name";
          leaf name {
            type string;
          }
          uses ncs_compliance_template_ipv6-route-grouping;
        }
      }
      container prefix-list {
        list prefixes {
          // NCS patched for predictable order
          ordered-by user;
          tailf:cli-drop-node-name;
          tailf:cli-suppress-mode;
          key "name";
          leaf name {
            type string;
          }
          leaf description {
            type string;
          }
          leaf permit {
            type ios:ncs_compliance_template_ipv6-prefix;
          }
          list seq {
            // NCS patched for predictable order
            ordered-by user;
            tailf:cli-suppress-mode;
            key "no";
            leaf no {
              type string;
            }
            container deny {
              leaf ip {
                tailf:cli-drop-node-name;
                type ios:ncs_compliance_template_ipv6-prefix;
              }
              leaf ge {
                type string;
              }
              leaf le {
                type string;
              }
            }
            container permit {
              leaf ip {
                tailf:cli-drop-node-name;
                type ios:ncs_compliance_template_ipv6-prefix;
              }
              leaf ge {
                type string;
              }
              leaf le {
                type string;
              }
            }
          }
        }
        leaf sequence-number {
          type empty;
        }
      }
    }
    container vlan {
      container accounting;
      container internal {
        container allocation {
          leaf policy {
            type string;
          }
        }
      }
      container dot1q {
        container tag {
          leaf native {
            type empty;
          }
        }
      }
      container access-log {
        leaf maxflow {
          type string;
        }
        leaf ratelimit {
          type string;
        }
        leaf threshold {
          type string;
        }
      }
      list vlan-list {
        // NCS patched for predictable order
        ordered-by user;
        tailf:cli-drop-node-name;
        tailf:cli-range-list-syntax;
        key "id";
        leaf id {
          type string;
        }
        leaf name {
          type string;
        }
        leaf uni-vlan {
          type string;
        }
      }
    }
    container interface {
      // NCS drop tailf-common:cli-diff-dependency statement
      list Embedded-Service-Engine {
        // NCS patched for predictable order
        ordered-by user;
        key "name";
        leaf name {
          type string;
        }
        uses ncs_compliance_template_interface-common-grouping;
      }
      list FastEthernet {
        // NCS patched for predictable order
        ordered-by user;
        key "name";
        leaf name {
          type string;
        }
        uses ncs_compliance_template_interface-ethernet-grouping;
        uses ncs_compliance_template_interface-common-grouping;
        uses ncs_compliance_template_interface-zone-member-grouping;
        uses ncs_compliance_template_interface-switch-grouping;
      }
      list GigabitEthernet {
        // NCS patched for predictable order
        ordered-by user;
        key "name";
        leaf name {
          type string;
        }
        leaf media-type {
          type string;
        }
        leaf port-type {
          type string;
        }
        uses ncs_compliance_template_interface-ethernet-grouping;
        uses ncs_compliance_template_interface-common-grouping;
        uses ncs_compliance_template_interface-zone-member-grouping;
        uses ncs_compliance_template_interface-switch-grouping;
      }
      list TenGigabitEthernet {
        // NCS patched for predictable order
        ordered-by user;
        key "name";
        leaf name {
          type string;
        }
        leaf media-type {
          type string;
        }
        leaf port-type {
          type string;
        }
        uses ncs_compliance_template_interface-ethernet-grouping;
        uses ncs_compliance_template_interface-common-grouping;
        uses ncs_compliance_template_interface-zone-member-grouping;
        uses ncs_compliance_template_interface-switch-grouping;
      }
      list Loopback {
        // NCS patched for predictable order
        ordered-by user;
        key "name";
        leaf name {
          type string;
        }
        uses ncs_compliance_template_interface-common-grouping;
      }
      list Port-channel {
        // NCS patched for predictable order
        ordered-by user;
        key "name";
        leaf name {
          type string;
        }
        leaf speed {
          type string;
        }
        uses ncs_compliance_template_interface-common-grouping;
        uses ncs_compliance_template_interface-switch-grouping;
      }
      list Vlan {
        // NCS patched for predictable order
        ordered-by user;
        key "name";
        leaf name {
          type string;
        }
        uses ncs_compliance_template_interface-common-grouping;
        uses ncs_compliance_template_interface-zone-member-grouping;
      }
      list Group-Async {
        // NCS patched for predictable order
        ordered-by user;
        key "name";
        leaf name {
          type string;
        }
        leaf physical-layer {
          type string;
        }
        uses ncs_compliance_template_interface-common-grouping;
      }
      list Multilink {
        // NCS patched for predictable order
        ordered-by user;
        key "name";
        leaf name {
          type string;
        }
        uses ncs_compliance_template_interface-common-grouping;
        uses ncs_compliance_template_interface-pointtopoint-grouping;
      }
      list Serial {
        // NCS patched for predictable order
        ordered-by user;
        key "name";
        leaf name {
          type string;
        }
        uses ncs_compliance_template_interface-common-grouping;
        uses ncs_compliance_template_interface-pointtopoint-grouping;
      }
      list Virtual-Template {
        // NCS patched for predictable order
        ordered-by user;
        key "name";
        leaf name {
          type string;
        }
        uses ncs_compliance_template_interface-ethernet-grouping;
        uses ncs_compliance_template_interface-common-grouping;
        uses ncs_compliance_template_interface-zone-member-grouping;
        uses ncs_compliance_template_interface-switch-grouping;
        uses ncs_compliance_template_interface-pointtopoint-grouping;
      }
    }
    list route-map {
      // NCS patched for predictable order
      ordered-by user;
      key "name sequence";
      leaf name {
        type string;
      }
      leaf sequence {
        tailf:cli-drop-node-name;
        type string;
      }
      leaf operation {
        tailf:cli-drop-node-name;
        type string;
        // NCS drop default statement
      }
      container set {
        container as-path {
          container prepend {
            container as-container {
              tailf:cli-drop-node-name;
              leaf as-number {
                tailf:cli-drop-node-name;
                type string;
              }
            }
            container last-as-cont {
              tailf:cli-drop-node-name;
              leaf last-as {
                type string;
              }
            }
          }
          container tag {
            presence "tag";
          }
        }
        container community {
          choice community-choice {
            case community-numberi-case {
              leaf community-number {
                tailf:cli-drop-node-name;
                type string;
              }
              leaf community-number-alt-format {
                tailf:cli-drop-node-name;
                type string;
              }
            }
            case well-known-community-case {
              leaf well-known-communities {
                tailf:cli-drop-node-name;
                type string;
              }
            }
          }
          leaf additive {
            type empty;
          }
        }
        container comm-list {
          choice comm-list-choice {
            leaf comm-list-standard {
              tailf:cli-drop-node-name;
              type string;
            }
            leaf comm-list-expanded {
              tailf:cli-drop-node-name;
              type string;
            }
            leaf comm-list-name {
              tailf:cli-drop-node-name;
              type string;
            }
          }
          leaf delete {
            type empty;
          }
        }
        container extcommunity {
          leaf-list rt {
            // NCS patched for predictable order
            ordered-by user;
            type ncs_compliance_template_asn-ip-type;
          }
        }
        container ip {
          container next-hop {
            choice next-hop-choice {
              leaf-list address {
                // NCS patched for predictable order
                ordered-by user;
                tailf:cli-drop-node-name;
                type string;
              }
              container dynamic {
                leaf dhcp {
                  type empty;
                }
              }
              leaf peer-address {
                type empty;
              }
            }
          }
        }
        leaf metric {
          type string;
        }
        leaf metric-type {
          type string;
        }
        leaf weight {
          type string;
        }
        container origin {
          choice origin-choice {
            leaf origin-value {
              tailf:cli-drop-node-name;
              type string;
            }
            leaf egp {
              type string;
            }
          }
        }
      }
      container match {
        container community {
          leaf-list name {
            // NCS patched for predictable order
            ordered-by user;
            tailf:cli-drop-node-name;
            type string;
          }
        }
        container ip {
          container address {
            choice address-choice {
              leaf access-list {
                tailf:cli-drop-node-name;
                type ncs_compliance_template_exp-acl-type;
              }
              leaf prefix-list {
                type string;
              }
            }
          }
        }
        container ipv6 {
          container address {
            choice address-choice {
              leaf access-list {
                tailf:cli-drop-node-name;
                type string;
              }
              leaf prefix-list {
                type string;
              }
            }
          }
        }
      }
    }
    container authentication {
      container mac-move {
        leaf permit {
          type empty;
        }
      }
    }
    container banner {
      container exec {
        leaf start-marker {
          tailf:cli-drop-node-name;
          type string;
        }
        leaf message {
          tailf:cli-drop-node-name;
          type string;
        }
        leaf end-marker {
          tailf:cli-drop-node-name;
          type string;
          // NCS drop must statement
        }
      }
      container login {
        leaf start-marker {
          tailf:cli-drop-node-name;
          type string;
        }
        leaf message {
          tailf:cli-drop-node-name;
          type string;
        }
        leaf end-marker {
          tailf:cli-drop-node-name;
          type string;
          // NCS drop must statement
        }
      }
      container prompt-timeout {
        leaf start-marker {
          tailf:cli-drop-node-name;
          type string;
        }
        leaf message {
          tailf:cli-drop-node-name;
          type string;
        }
        leaf end-marker {
          tailf:cli-drop-node-name;
          type string;
          // NCS drop must statement
        }
      }
      container motd {
        leaf start-marker {
          tailf:cli-drop-node-name;
          type string;
        }
        leaf message {
          tailf:cli-drop-node-name;
          type string;
        }
        leaf end-marker {
          tailf:cli-drop-node-name;
          type string;
          // NCS drop must statement
        }
      }
    }
    list table-map {
      // NCS patched for predictable order
      ordered-by user;
      key "name";
      leaf name {
        type string;
      }
      leaf default {
        type string;
      }
      list map {
        // NCS patched for predictable order
        ordered-by user;
        tailf:cli-suppress-mode;
        key "from to";
        leaf from {
          type string;
        }
        leaf to {
          type string;
        }
      }
    }
    container mls {
      container acl {
        container tcam {
          leaf default-result {
            type string;
          }
          container log-update {
            presence "true";
            leaf rate-limit-msg {
              type string;
            }
          }
          leaf share-global {
            type string;
            // NCS drop default statement
          }
        }
      }
      container cef {
        container error {
          leaf action {
            type string;
          }
        }
      }
      container flow {
        leaf ip {
          type string;
        }
      }
      container ip {
        container multicast {
          presence "true";
          container consistency-check {
            presence "true";
            leaf settle-time {
              type string;
            }
          }
          leaf flow-stat-timer {
            type string;
          }
        }
      }
      container mls-qos-conf {
        tailf:cli-drop-node-name;
        leaf qos {
          type empty;
        }
      }
      container qos {
        list aggregate-policer {
          // NCS patched for predictable order
          ordered-by user;
          tailf:cli-suppress-mode;
          key "name";
          leaf name {
            type string;
          }
          leaf target-bit-rate {
            tailf:cli-drop-node-name;
            type string;
          }
          leaf burst-normal {
            tailf:cli-drop-node-name;
            type string;
          }
          leaf burst-max {
            tailf:cli-drop-node-name;
            // NCS drop when statement
            type string;
          }
          leaf pir {
            type string;
          }
          container conform-action {
            choice action-choice {
              leaf drop {
                type empty;
              }
              leaf set-dscp-transmit {
                type ncs_compliance_template_dscp-type;
              }
              leaf set-mpls-exp-imposition-transmit {
                type string;
              }
              leaf set-prec-transmit {
                type string;
              }
              leaf transmit {
                type empty;
              }
            }
          }
          leaf exceed-action {
            type string;
          }
          leaf violate-action {
            type string;
          }
        }
        container rewrite {
          container ip {
            container dscp {
              presence "true";
              leaf slot {
                type string;
              }
            }
          }
        }
      }
      container rate-limit {
        container layer2 {
          container l2pt {
            leaf packets-per-second {
              tailf:cli-drop-node-name;
              type string;
            }
            leaf packets-in-burst {
              tailf:cli-drop-node-name;
              type string;
            }
          }
          container pdu {
            leaf packets-per-second {
              tailf:cli-drop-node-name;
              type string;
            }
            leaf packets-in-burst {
              tailf:cli-drop-node-name;
              type string;
            }
          }
        }
      }
      container verify {
        container ip {
          leaf checksum {
            type string;
            // NCS drop default statement
          }
          container length {
            leaf consistent {
              type string;
              // NCS drop default statement
            }
            leaf minimum {
              type string;
              // NCS drop default statement
            }
          }
          leaf same-address {
            type empty;
          }
          leaf syslog {
            type empty;
          }
        }
      }
    }
    container policer {
      list aggregate {
        // NCS patched for predictable order
        ordered-by user;
        tailf:cli-suppress-mode;
        key "name";
        leaf name {
          type string;
        }
        leaf cir {
          type string;
        }
        leaf bc {
          type string;
        }
        leaf conform-action {
          type empty;
        }
        leaf set-qos-transmit {
          // NCS drop when statement
          type string;
        }
        leaf set-dot1ad-dei-transmit {
          // NCS drop when statement
          type string;
        }
        leaf set-prec-transmit {
          // NCS drop when statement
          type ncs_compliance_template_prec_value-type;
        }
        container set-prec-transmit-table {
          // NCS drop when statement
          tailf:cli-drop-node-name;
          leaf table {
            type string;
          }
        }
        leaf set-dscp-transmit {
          // NCS drop when statement
          type ncs_compliance_template_dscp-type;
        }
        container set-dscp-transmit-table {
          // NCS drop when statement
          tailf:cli-drop-node-name;
          leaf table {
            type string;
          }
        }
        leaf set-cos-transmit {
          // NCS drop when statement
          type ncs_compliance_template_cos_value-type;
        }
        container set-cos-transmit-table {
          // NCS drop when statement
          tailf:cli-drop-node-name;
          leaf table {
            type string;
          }
        }
        leaf transmit {
          // NCS drop when statement
          type empty;
        }
        leaf exceed-action {
          type empty;
        }
        leaf drop {
          // NCS drop when statement
          type empty;
        }
        container exceed-transmit {
          tailf:cli-drop-node-name;
          leaf transmit {
            // NCS drop when statement
            type empty;
          }
        }
      }
    }
    list class-map {
      // NCS patched for predictable order
      ordered-by user;
      key "name";
      leaf name {
        type string;
      }
      leaf type {
        type string;
      }
      leaf protocol {
        tailf:cli-drop-node-name;
        type string;
      }
      leaf prematch {
        tailf:cli-drop-node-name;
        type string;
        // NCS drop mandatory statement
      }
      leaf description {
        type string;
      }
      container match {
        uses ncs_compliance_template_class-map-match-grouping;
        container not {
          uses ncs_compliance_template_class-map-match-grouping;
        }
      }
    }
    list policy-map {
      // NCS patched for predictable order
      ordered-by user;
      // NCS drop tailf-common:cli-diff-dependency statement
      // NCS drop tailf-common:cli-diff-dependency statement
      // NCS drop tailf-common:cli-diff-dependency statement
      // NCS drop tailf-common:cli-diff-dependency statement
      key "name";
      leaf name {
        type string;
      }
      leaf type {
        type string;
      }
      leaf protocol {
        tailf:cli-drop-node-name;
        type string;
      }
      list class {
        // NCS patched for predictable order
        ordered-by user;
        key "name";
        leaf name {
          type ncs_compliance_template_class-name-type;
        }
        leaf type {
          type string;
        }
        container policy {
          // NCS drop when statement
          tailf:cli-drop-node-name;
          leaf action {
            tailf:cli-drop-node-name;
            type string;
          }
          leaf log {
            // NCS drop when statement
            type empty;
          }
          leaf parameter-map {
            tailf:cli-drop-node-name;
            // NCS drop when statement
            type string;
          }
        }
        container inspect-police {
          // NCS drop when statement
          tailf:cli-drop-node-name;
          container police {
            leaf rate {
              type string;
            }
            leaf burst {
              type string;
            }
          }
        }
        container bandwidth {
          leaf bits {
            tailf:cli-drop-node-name;
            type string;
          }
          leaf percent {
            type ncs_compliance_template_percentage-type;
          }
          container remaining {
            leaf percent {
              type ncs_compliance_template_percentage-type;
            }
          }
        }
        container compression {
          presence "Activate Compression";
          container header {
            presence "configure header compression";
            leaf ip {
              type string;
            }
          }
        }
        leaf drop {
          type empty;
        }
        container estimate {
          container bandwidth {
            presence "bandwidth required to service this class";
            container delay-one-in {
              leaf doi {
                tailf:cli-drop-node-name;
                type string;
              }
              leaf milliseconds {
                type string;
              }
            }
            leaf drop-one-in {
              type string;
            }
          }
        }
        container fair-queue {
          presence "true";
          leaf dynamic-queues {
            tailf:cli-drop-node-name;
            type string;
          }
          leaf queue-limit {
            type string;
          }
        }
        leaf netflow-sampler {
          type string;
        }
        choice police-choice {
          case police-aggregate-case {
            container police-aggregate {
              tailf:cli-drop-node-name;
              container police {
                leaf aggregate {
                  type string;
                }
              }
            }
          }
          case police-policy-map-case {
            container police-policy-map {
              tailf:cli-drop-node-name;
              container police {
                leaf cir {
                  type ncs_compliance_template_police-bps-type;
                }
                leaf bc {
                  type ncs_compliance_template_police-burst-type;
                }
                leaf be {
                  // NCS drop when statement
                  type ncs_compliance_template_police-burst-type;
                }
                leaf pir {
                  type ncs_compliance_template_police-bps-type;
                }
                container pir-be {
                  // NCS drop when statement
                  tailf:cli-drop-node-name;
                  leaf be {
                    type ncs_compliance_template_police-burst-type;
                  }
                }
                uses ncs_compliance_template_police-action-grouping;
              }
            }
          }
          case police-cir-percent-case {
            container police-cir-percent {
              tailf:cli-drop-node-name;
              container police {
                container cir {
                  container percent {
                    leaf percentage {
                      tailf:cli-drop-node-name;
                      type ncs_compliance_template_percentage-type;
                    }
                    leaf bc {
                      type string;
                    }
                    container bc-ms {
                      // NCS drop when statement
                      tailf:cli-drop-node-name;
                      leaf ms {
                        type empty;
                      }
                    }
                    leaf be {
                      // NCS drop when statement
                      type string;
                    }
                    container be-ms {
                      // NCS drop when statement
                      tailf:cli-drop-node-name;
                      leaf ms {
                        type empty;
                      }
                    }
                    container pir {
                      leaf percent {
                        type ncs_compliance_template_percentage-type;
                      }
                    }
                    container pir-be {
                      // NCS drop when statement
                      tailf:cli-drop-node-name;
                      leaf be {
                        type string;
                      }
                    }
                    container pir-be-ms {
                      // NCS drop when statement
                      tailf:cli-drop-node-name;
                      leaf ms {
                        type empty;
                      }
                    }
                    uses ncs_compliance_template_police-action-grouping;
                  }
                }
              }
            }
          }
          case police-rate-unit-case {
            container police-rate-unit {
              tailf:cli-drop-node-name;
              container police {
                container rate {
                  leaf units {
                    tailf:cli-drop-node-name;
                    type string;
                  }
                  leaf xps {
                    tailf:cli-drop-node-name;
                    type ncs_compliance_template_police-pps-bps-type;
                  }
                  container burst {
                    leaf burst-value {
                      tailf:cli-drop-node-name;
                      type string;
                    }
                    leaf burst-type {
                      tailf:cli-drop-node-name;
                      type ncs_compliance_template_police-packets-bytes-type;
                    }
                  }
                  container peak-rate {
                    leaf peak-rate-value {
                      tailf:cli-drop-node-name;
                      type string;
                    }
                    leaf xps {
                      tailf:cli-drop-node-name;
                      type ncs_compliance_template_police-pps-bps-type;
                    }
                  }
                  container peak-burst {
                    leaf burst-value {
                      tailf:cli-drop-node-name;
                      type string;
                    }
                    leaf burst-type {
                      tailf:cli-drop-node-name;
                      type ncs_compliance_template_police-packets-bytes-type;
                    }
                  }
                  uses ncs_compliance_template_police-action-grouping;
                }
              }
            }
          }
          case police-rate-percent-case {
            container police-rate-percent {
              tailf:cli-drop-node-name;
              container police {
                container rate {
                  container percent {
                    leaf percentage {
                      tailf:cli-drop-node-name;
                      type ncs_compliance_template_percentage-type;
                    }
                    leaf burst {
                      type string;
                    }
                    leaf ms {
                      // NCS drop when statement
                      type empty;
                    }
                    container peak-rate {
                      leaf percent {
                        type ncs_compliance_template_percentage-type;
                      }
                    }
                    leaf peak-burst {
                      type string;
                    }
                    container peak-burst-ms {
                      // NCS drop when statement
                      tailf:cli-drop-node-name;
                      leaf ms {
                        type empty;
                      }
                    }
                    uses ncs_compliance_template_police-action-grouping;
                  }
                }
              }
            }
          }
          case police-rate-pdp-case {
            container police-rate-pdp {
              tailf:cli-drop-node-name;
              container police {
                container rate {
                  container pdp {
                    leaf burst {
                      type ncs_compliance_template_police-burst-type;
                    }
                    leaf peak-rate {
                      type string;
                    }
                    leaf peak-burst {
                      // NCS drop when statement
                      type ncs_compliance_template_police-burst-type;
                    }
                    uses ncs_compliance_template_police-action-grouping;
                  }
                }
              }
            }
          }
          case police-flow-case {
            container police-flow {
              tailf:cli-drop-node-name;
              container police {
                container flow {
                  leaf mask {
                    type string;
                  }
                  leaf bps {
                    tailf:cli-drop-node-name;
                    type ncs_compliance_template_police-bps-type;
                  }
                  leaf burst-normal {
                    // NCS drop when statement
                    tailf:cli-drop-node-name;
                    type ncs_compliance_template_police-burst-type;
                  }
                  uses ncs_compliance_template_police-action-grouping;
                }
              }
            }
          }
          case police-catalyst-case {
            container police-catalyst {
              tailf:cli-drop-node-name;
              container police {
                leaf bps-value {
                  tailf:cli-drop-node-name;
                  type string;
                }
                leaf bps {
                  type empty;
                }
                leaf byte-value {
                  tailf:cli-drop-node-name;
                  type string;
                }
                leaf byte {
                  type empty;
                }
                container actions {
                  tailf:cli-drop-node-name;
                  uses ncs_compliance_template_police-conform-action-grouping;
                  uses ncs_compliance_template_police-exceed-action-grouping;
                  uses ncs_compliance_template_police-violate-action-grouping;
                }
              }
            }
          }
          case police-switch-case {
            container police-switch {
              tailf:cli-drop-node-name;
              container police {
                leaf cir {
                  tailf:cli-drop-node-name;
                  type string;
                }
                leaf bc {
                  tailf:cli-drop-node-name;
                  type string;
                }
                leaf exceed-action {
                  type string;
                }
              }
            }
          }
        }
        container priority {
          presence "true";
          leaf level {
            type string;
          }
          choice priority-type {
            leaf kilo-bits {
              tailf:cli-drop-node-name;
              type string;
            }
            leaf percent {
              type string;
            }
          }
          leaf burst {
            tailf:cli-drop-node-name;
            type string;
          }
        }
        container queue-limit {
          leaf queue-limit-value {
            tailf:cli-drop-node-name;
            type string;
          }
          leaf queue-limit-type {
            tailf:cli-drop-node-name;
            type string;
          }
        }
        container random-detect {
          presence "true";
          container aggregate {
            presence "true";
            leaf minimum-thresh {
              type string;
            }
            leaf maximum-thresh {
              type string;
            }
            leaf mark-probability {
              type empty;
            }
            leaf denominator {
              tailf:cli-drop-node-name;
              type string;
            }
          }
          container discard-class {
            leaf dclass {
              tailf:cli-drop-node-name;
              type string;
            }
            uses ncs_compliance_template_random-detect-grouping;
          }
          leaf discard-class-based {
            type empty;
          }
          container dscp {
            leaf dscp-val {
              tailf:cli-drop-node-name;
              type ncs_compliance_template_dscp-type;
            }
            uses ncs_compliance_template_random-detect-grouping;
          }
          leaf dscp-based {
            type empty;
          }
          leaf ecn {
            type empty;
          }
          leaf exponential-weighting-constant {
            type string;
          }
          leaf prec-based {
            type empty;
          }
          container precedence {
            leaf prec {
              tailf:cli-drop-node-name;
              type ncs_compliance_template_precedence-type2;
            }
            uses ncs_compliance_template_random-detect-grouping;
          }
        }
        leaf service-policy {
          type string;
        }
        container set {
          leaf atm-clp {
            type empty;
          }
          container cos {
            choice cos-type {
              case a {
                leaf val {
                  tailf:cli-drop-node-name;
                  type string;
                }
              }
              case b {
                leaf pack {
                  tailf:cli-drop-node-name;
                  type string;
                }
                leaf table {
                  type string;
                }
              }
            }
          }
          leaf discard-class {
            type string;
          }
          leaf dscp {
            type ncs_compliance_template_dscp-type;
          }
          leaf fr-de {
            type empty;
          }
          container ip {
            choice ip-choice {
              leaf dscp {
                type ncs_compliance_template_dscp-type;
              }
              container precedence {
                presence "Set IP precedence";
                leaf precedence-val {
                  tailf:cli-drop-node-name;
                  type ncs_compliance_template_precedence-type;
                }
              }
            }
          }
          container mpls {
            container experimental {
              container imposition {
                leaf exp-value {
                  tailf:cli-drop-node-name;
                  type string;
                }
              }
            }
          }
          container qos-group {
            leaf qos-group-value {
              tailf:cli-drop-node-name;
              type string;
            }
          }
        }
        container shape {
          leaf adaptive {
            type string;
          }
          container average {
            choice average-choice {
              case a {
                leaf bit-rate {
                  tailf:cli-drop-node-name;
                  type string;
                }
                leaf bits-per-interval-sustained {
                  tailf:cli-drop-node-name;
                  type string;
                }
                leaf bits-per-interval-excess {
                  tailf:cli-drop-node-name;
                  type string;
                }
              }
              case b {
                leaf percent {
                  type ncs_compliance_template_percentage-type;
                }
                leaf burst-size-sustained {
                  tailf:cli-drop-node-name;
                  type string;
                }
                leaf ms {
                  type empty;
                }
                container bse {
                  tailf:cli-drop-node-name;
                  leaf burst-size-excess {
                    type string;
                  }
                  leaf ms {
                    type empty;
                  }
                }
              }
            }
          }
          leaf fecn-adapt {
            type empty;
          }
          container fr-voice-adapt {
            presence "Enable rate adjustment depending on voice presence";
            leaf deactivation {
              type string;
            }
          }
          leaf max-buffers {
            type string;
          }
        }
        leaf trust {
          type string;
        }
      }
      leaf description {
        type string;
      }
    }
    container control-plane {
      presence "true";
      container service-policy {
        leaf input {
          type string;
        }
        leaf output {
          type string;
        }
      }
    }
    leaf config-register {
      type string;
    }
    container clock {
      container calendar-valid {
        presence "true";
      }
      container summer-time {
        leaf zone {
          tailf:cli-drop-node-name;
          type string;
        }
        choice summer-choice {
          case date-case {
            leaf date {
              type empty;
            }
          }
          case recurring-case {
            leaf recurring {
              type empty;
            }
            leaf start {
              tailf:cli-drop-node-name;
              type string;
            }
            leaf start-day {
              tailf:cli-drop-node-name;
              type ncs_compliance_template_weekday-type;
            }
            leaf start-month {
              tailf:cli-drop-node-name;
              type ncs_compliance_template_month-type;
            }
            leaf start-time {
              tailf:cli-drop-node-name;
              type ncs_compliance_template_hhmm-type;
            }
            leaf end {
              tailf:cli-drop-node-name;
              type string;
            }
            leaf end-day {
              tailf:cli-drop-node-name;
              type ncs_compliance_template_weekday-type;
            }
            leaf end-month {
              tailf:cli-drop-node-name;
              type ncs_compliance_template_month-type;
            }
            leaf end-time {
              tailf:cli-drop-node-name;
              type ncs_compliance_template_hhmm-type;
            }
          }
        }
      }
      container timezone {
        leaf zone {
          tailf:cli-drop-node-name;
          type string;
        }
        leaf offset {
          tailf:cli-drop-node-name;
          type string;
        }
        leaf hours {
          tailf:cli-drop-node-name;
          type string;
        }
        leaf minutes {
          tailf:cli-drop-node-name;
          type string;
        }
      }
    }
    container gatekeeper {
      leaf shutdown {
        type empty;
      }
    }
    container line {
      list aux {
        // NCS patched for predictable order
        ordered-by user;
        key "first";
        // NCS drop max-elements statement
        leaf first {
          type string;
        }
        uses ncs_compliance_template_line-grouping;
      }
      list console {
        // NCS patched for predictable order
        ordered-by user;
        key "first";
        // NCS drop max-elements statement
        leaf first {
          type string;
        }
        uses ncs_compliance_template_line-grouping;
      }
      container vty-single {
        tailf:cli-drop-node-name;
        list vty {
          // NCS patched for predictable order
          ordered-by user;
          key "first";
          leaf first {
            type string;
          }
          uses ncs_compliance_template_line-grouping;
        }
      }
      list vty {
        // NCS patched for predictable order
        ordered-by user;
        key "first last";
        leaf first {
          type string;
        }
        leaf last {
          type string;
        }
        uses ncs_compliance_template_line-grouping;
      }
    }
    container logging {
      leaf alarm {
        type string;
      }
      container buffered {
        leaf size {
          tailf:cli-drop-node-name;
          type string;
        }
        leaf severity {
          tailf:cli-drop-node-name;
          type ncs_compliance_template_logging-level-type;
        }
        leaf xxml {
          tailf:alt-name "xml";
          type string;
        }
      }
      leaf console {
        type string;
      }
      container event {
        container link-status {
          leaf boot {
            type empty;
          }
          leaf global {
            type empty;
          }
          leaf default {
            type empty;
          }
        }
      }
      container esm {
        leaf config {
          type empty;
        }
      }
      leaf facility {
        type string;
      }
      container history {
        leaf size {
          type string;
        }
        leaf severity-level {
          tailf:cli-drop-node-name;
          type string;
        }
      }
      list hostname {
        // NCS patched for predictable order
        ordered-by user;
        tailf:cli-drop-node-name;
        tailf:cli-suppress-mode;
        key "host";
        leaf host {
          type string;
        }
      }
      list host {
        // NCS patched for predictable order
        ordered-by user;
        tailf:cli-suppress-mode;
        key "host";
        leaf host {
          type string;
        }
        leaf vrf {
          type string;
        }
        leaf discriminator {
          type string;
        }
      }
      container rate-limit {
        leaf console {
          type empty;
        }
        leaf all {
          type empty;
        }
        leaf rate {
          tailf:cli-drop-node-name;
          type string;
        }
      }
      container source-interface {
        // NCS drop tailf-common:cli-diff-dependency statement
        uses ncs_compliance_template_interface-grouping;
      }
      leaf trap {
        type ncs_compliance_template_logging-level-type;
      }
    }
    container mgcp {
      container fax {
        container t38 {
          leaf ecm {
            type empty;
          }
        }
      }
      container profile {
        leaf default {
          type empty;
        }
      }
    }
    container multilink {
      leaf bundle-name {
        type string;
      }
      leaf virtual-template {
        type string;
      }
    }
    container ntp {
      // NCS drop tailf-common:cli-diff-dependency statement
      container access-group {
        leaf peer {
          type string;
        }
        leaf serve {
          type string;
        }
      }
      container server {
        uses ncs_compliance_template_ntp-server-grouping;
        list vrf {
          // NCS patched for predictable order
          ordered-by user;
          tailf:cli-suppress-mode;
          // NCS drop tailf-common:cli-diff-dependency statement
          // NCS drop tailf-common:cli-diff-dependency statement
          key "name";
          leaf name {
            type string;
          }
          uses ncs_compliance_template_ntp-server-grouping;
        }
      }
      container source {
        uses ncs_compliance_template_interface-grouping;
      }
      leaf update-calendar {
        type empty;
      }
    }
    container no {
      container mac-address-table {
        container learning {
          list vlan {
            // NCS patched for predictable order
            ordered-by user;
            tailf:cli-suppress-mode;
            key "id";
            leaf id {
              type string;
            }
            leaf module {
              type string;
            }
          }
        }
      }
    }
    container privilege {
      container exec {
        list level {
          // NCS patched for predictable order
          ordered-by user;
          tailf:cli-suppress-mode;
          key "privilege";
          leaf privilege {
            type string;
          }
          list command-list {
            // NCS patched for predictable order
            ordered-by user;
            tailf:cli-suppress-mode;
            tailf:cli-drop-node-name;
            key "command";
            leaf command {
              tailf:cli-drop-node-name;
              type string;
            }
          }
        }
      }
    }
    container redundancy {
      leaf maintenance-mode {
        type empty;
      }
      container main-cpu {
        container auto-sync {
          leaf running-config {
            type empty;
          }
          leaf config-register {
            type empty;
          }
          leaf bootvar {
            type empty;
          }
        }
      }
      leaf mode {
        type string;
      }
    }
    container scheduler {
      container allocate {
        leaf interrupt-time {
          tailf:cli-drop-node-name;
          type string;
        }
        leaf process-time {
          tailf:cli-drop-node-name;
          type string;
        }
      }
    }
    container spanning-tree {
      container etherchannel {
        container guard {
          leaf misconfig {
            type empty;
          }
        }
      }
      container extend {
        leaf system-id {
          type empty;
        }
      }
      container loopguard {
        leaf default {
          type empty;
        }
      }
      container mst {
        list instance-range {
          // NCS patched for predictable order
          ordered-by user;
          tailf:cli-suppress-mode;
          tailf:cli-drop-node-name;
          tailf:cli-range-list-syntax;
          key "id";
          leaf id {
            type string;
          }
          leaf priority {
            type string;
          }
        }
        container configuration {
          leaf name {
            type string;
          }
          list instance {
            // NCS patched for predictable order
            ordered-by user;
            tailf:cli-suppress-mode;
            key "id";
            leaf id {
              type string;
            }
            leaf-list vlan {
              // NCS patched for predictable order
              ordered-by user;
              tailf:cli-range-list-syntax;
              type string;
            }
          }
        }
      }
      container optimize {
        container bpdu {
          leaf transmission {
            type string;
          }
        }
      }
      container portfast {
        leaf bdpu {
          tailf:cli-drop-node-name;
          type string;
        }
        leaf default {
          type empty;
        }
      }
      leaf mode {
        type string;
      }
      container vlans-max-age {
        tailf:cli-drop-node-name;
        list vlan {
          // NCS patched for predictable order
          ordered-by user;
          tailf:cli-range-list-syntax;
          tailf:cli-suppress-mode;
          key "id";
          leaf id {
            type string;
          }
          leaf max-age {
            type string;
          }
        }
      }
      container vlans-forward-time {
        tailf:cli-drop-node-name;
        list vlan {
          // NCS patched for predictable order
          ordered-by user;
          tailf:cli-range-list-syntax;
          tailf:cli-suppress-mode;
          key "id";
          leaf id {
            type string;
          }
          leaf forward-time {
            type string;
          }
        }
      }
      container vlans-hello-time {
        tailf:cli-drop-node-name;
        list vlan {
          // NCS patched for predictable order
          ordered-by user;
          tailf:cli-range-list-syntax;
          tailf:cli-suppress-mode;
          key "id";
          leaf id {
            type string;
          }
          leaf hello-time {
            type string;
          }
        }
      }
      container vlans-priority {
        tailf:cli-drop-node-name;
        list vlan {
          // NCS patched for predictable order
          ordered-by user;
          tailf:cli-range-list-syntax;
          tailf:cli-suppress-mode;
          key "id";
          leaf id {
            type string;
          }
          leaf priority {
            type string;
          }
        }
      }
      container vlans-root {
        tailf:cli-drop-node-name;
        list vlan {
          // NCS patched for predictable order
          ordered-by user;
          tailf:cli-range-list-syntax;
          tailf:cli-suppress-mode;
          key "id";
          leaf id {
            type string;
          }
          container root {
            container primary {
              leaf diameter {
                type string;
              }
              leaf hello-time {
                type string;
              }
            }
            container secondary {
              leaf diameter {
                type string;
              }
              leaf hello-time {
                type string;
              }
            }
          }
        }
      }
    }
    container dot1x {
      container critical {
        leaf eapol {
          type empty;
        }
        container recovery {
          leaf delay {
            type string;
          }
        }
      }
      leaf system-auth-control {
        type empty;
      }
    }
    container power {
      leaf redundancy-mode {
        type string;
      }
    }
    container parameter-map {
      container type {
        list inspect {
          // NCS patched for predictable order
          ordered-by user;
          key "id";
          leaf id {
            type string;
          }
          leaf alert {
            type string;
          }
          leaf audit-trail {
            type string;
          }
          leaf dns-timeout {
            type string;
          }
          container icmp {
            leaf idle-time {
              type string;
            }
          }
          container max-incomplete {
            leaf high {
              type string;
            }
            leaf low {
              type string;
            }
          }
          container one-minute {
            leaf high {
              type string;
            }
            leaf low {
              type string;
            }
          }
          container sessions {
            leaf maximum {
              type string;
            }
          }
          container tcp {
            leaf finwait-time {
              type string;
            }
            leaf idle-time {
              type string;
            }
            container max-incomplete {
              leaf host {
                type string;
              }
            }
            leaf synwait-time {
              type string;
            }
          }
          container udp {
            leaf idle-time {
              type string;
            }
          }
        }
      }
    }
    container vpdn {
      leaf authen-before-forward {
        type empty;
      }
      leaf enable {
        type empty;
      }
      leaf-list search-order {
        // NCS patched for predictable order
        ordered-by user;
        type string;
      }
    }
    container bba-group {
      list pppoe {
        // NCS patched for predictable order
        ordered-by user;
        key "id";
        leaf id {
          type string;
        }
        container vendor-tag {
          container circuit-id {
            leaf service {
              type empty;
            }
          }
          container dsl-sync-rate {
            leaf service {
              type empty;
            }
          }
          container remote-id {
            leaf service {
              type empty;
            }
          }
          leaf strip {
            type empty;
          }
        }
        leaf virtual-template {
          type string;
        }
      }
    }
    container mac {
      container access-list {
        list extended {
          // NCS patched for predictable order
          ordered-by user;
          key "id";
          leaf id {
            type string;
          }
          container deny {
            container source {
              tailf:cli-drop-node-name;
              choice target-choice {
                leaf any {
                  type empty;
                }
                leaf host {
                  type string;
                }
              }
            }
            container dest {
              tailf:cli-drop-node-name;
              choice target-choice {
                leaf any {
                  type empty;
                }
                leaf host {
                  type string;
                }
              }
            }
          }
          container permit {
            container source {
              tailf:cli-drop-node-name;
              choice target-choice {
                leaf any {
                  type empty;
                }
                leaf host {
                  type string;
                }
              }
            }
            container dest {
              tailf:cli-drop-node-name;
              choice target-choice {
                leaf any {
                  type empty;
                }
                leaf host {
                  type string;
                }
              }
            }
          }
        }
      }
    }
    container tacacs-server {
      list host {
        // NCS patched for predictable order
        ordered-by user;
        tailf:cli-suppress-mode;
        key "name";
        leaf name {
          type ncs_compliance_template_host-type;
        }
        leaf port {
          type string;
        }
        leaf timeout {
          type string;
        }
      }
      leaf timeout {
        type string;
        // NCS drop default statement
      }
      container directed-request {
        presence "true";
        leaf restricted {
          type empty;
        }
        leaf no-truncate {
          type empty;
        }
      }
      container key {
        leaf encryption {
          tailf:cli-drop-node-name;
          type string;
        }
        leaf key {
          tailf:cli-drop-node-name;
          type string;
        }
      }
    }
    container upgrade {
      container fpd {
        leaf auto {
          type empty;
        }
        leaf path {
          type string;
        }
      }
    }
    container vtp {
      leaf file {
        type string;
      }
      leaf interface {
        type string;
      }
      leaf password {
        type string;
      }
      leaf pruning {
        type empty;
      }
      leaf version {
        type string;
      }
      leaf domain {
        type string;
      }
      leaf mode {
        type string;
      }
    }
    container rep {
      container admin {
        list vlan {
          // NCS patched for predictable order
          ordered-by user;
          key "name";
          leaf name {
            type string;
          }
        }
      }
    }
    container xconnect {
      container logging {
        container pseudowire {
          leaf status {
            type empty;
          }
        }
        leaf redundancy {
          type empty;
        }
      }
    }
    container fabric {
      container switching-mode {
        container allow {
          choice allow-choice {
            leaf bus-mode {
              type empty;
            }
            container truncated {
              presence "true";
              leaf threshold {
                type string;
              }
            }
          }
        }
        container force {
          leaf bus-mode {
            type empty;
          }
        }
      }
    }
    container port-channel {
      leaf load-balance {
        type string;
      }
    }
    container l2 {
      list vfi {
        // NCS patched for predictable order
        ordered-by user;
        tailf:cli-suppress-mode;
        key "name";
        leaf name {
          type string;
        }
        leaf point-to-point {
          type empty;
        }
      }
    }
    container l2protocol-tunnel {
      leaf cos {
        type string;
      }
      container global {
        leaf drop-threshold {
          type string;
        }
      }
    }
    container system {
      container env {
        container temperature {
          container threshold {
            leaf yellow {
              type string;
            }
          }
        }
      }
      container mtu {
        leaf size {
          tailf:cli-drop-node-name;
          type string;
        }
        leaf jumbo {
          type string;
        }
        leaf routing {
          type string;
        }
      }
    }
    container errdisable {
      container detect {
        container cause {
          leaf all {
            type empty;
          }
          leaf arp-inspection {
            type empty;
          }
          leaf bpduguard {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf loopback {
            type empty;
          }
          leaf mlacp-minlink {
            type empty;
          }
          leaf pagp-flap {
            type empty;
          }
          leaf pppoe-ia-rate-limit {
            type empty;
          }
          leaf security-violation {
            type empty;
          }
          leaf sfp-config-mismatch {
            type empty;
          }
          leaf small-frame {
            type empty;
          }
        }
      }
      container flap-setting {
        container cause {
          container dtp-flap {
            leaf max-flaps {
              type string;
            }
            leaf time {
              type string;
            }
          }
          container link-flap {
            leaf max-flaps {
              type string;
            }
            leaf time {
              type string;
            }
          }
          container pagp-flap {
            leaf max-flaps {
              type string;
            }
            leaf time {
              type string;
            }
          }
        }
      }
      container recovery {
        container cause {
          leaf all {
            type empty;
          }
          leaf arp-inspection {
            type empty;
          }
          leaf bpduguard {
            type empty;
          }
          leaf channel-misconfig {
            type empty;
          }
          leaf dhcp-rate-limit {
            type empty;
          }
          leaf dtp-flap {
            type empty;
          }
          leaf gbic-invalid {
            type empty;
          }
          leaf inline-power {
            type empty;
          }
          leaf l2ptguard {
            type empty;
          }
          leaf link-flap {
            type empty;
          }
          leaf link-monitor-failure {
            type empty;
          }
          leaf loopback {
            type empty;
          }
          leaf mac-limit {
            type empty;
          }
          leaf mlacp-minlink {
            type empty;
          }
          container oam-remote-failure {
            presence "true";
            leaf critical-event {
              type empty;
            }
            leaf dying-gasp {
              type empty;
            }
            leaf link-fault {
              type empty;
            }
          }
          leaf pagp-flap {
            type empty;
          }
          leaf port-mode-failure {
            type empty;
          }
          leaf pppoe-ia-rate-limit {
            type empty;
          }
          leaf psp {
            type empty;
          }
          leaf psecure-violation {
            type empty;
          }
          leaf security-violation {
            type empty;
          }
          leaf sfp-config-mismatch {
            type empty;
          }
          leaf small-frame {
            type empty;
          }
          leaf storm-control {
            type empty;
          }
          leaf udld {
            type empty;
          }
          leaf unicast-flood {
            type empty;
          }
          leaf vmps {
            type empty;
          }
        }
        leaf interval {
          type string;
        }
      }
    }
    container monitor {
      container event-trace;
      list session {
        // NCS patched for predictable order
        ordered-by user;
        tailf:cli-suppress-mode;
        key "id";
        leaf id {
          type string;
        }
        container destination {
          leaf interface {
            type string;
          }
          leaf encapsulation {
            type string;
          }
          leaf ingress {
            type empty;
          }
          leaf ingress-encap {
            tailf:cli-drop-node-name;
            // NCS drop when statement
            type string;
          }
          leaf vlan {
            // NCS drop when statement
            type string;
          }
        }
        container source {
          container interface {
            // NCS drop tailf-common:cli-diff-dependency statement
            uses ncs_compliance_template_interface-grouping;
          }
          container vlan {
            leaf vlan {
              tailf:cli-drop-node-name;
              type string;
            }
            leaf direction {
              tailf:cli-drop-node-name;
              type string;
            }
          }
        }
      }
    }
    list tftp-server {
      // NCS patched for predictable order
      ordered-by user;
      tailf:cli-suppress-mode;
      key "name";
      leaf name {
        type string;
      }
    }
    container radius-server {
      list host {
        // NCS patched for predictable order
        ordered-by user;
        tailf:cli-suppress-mode;
        key "id";
        leaf id {
          type string;
        }
        leaf acct-port {
          type string;
        }
        leaf auth-port {
          type string;
        }
        leaf key {
          type string;
        }
      }
    }
    container radius {
      list filter {
        // NCS patched for predictable order
        ordered-by user;
        key "id";
        leaf id {
          type string;
        }
        leaf match {
          tailf:cli-drop-node-name;
          type string;
        }
      }
      list server {
        // NCS patched for predictable order
        ordered-by user;
        key "id";
        leaf id {
          type string;
        }
        container address {
          container ipv4 {
            leaf host {
              tailf:cli-drop-node-name;
              type string;
            }
            leaf auth-port {
              type string;
            }
            leaf acct-port {
              type string;
            }
          }
        }
        container backoff {
          container exponential {
            presence "true";
            leaf max-delay {
              type string;
            }
            leaf backoff-retry {
              type string;
            }
          }
        }
        container key {
          leaf encryption {
            tailf:cli-drop-node-name;
            type string;
          }
          leaf key {
            tailf:cli-drop-node-name;
            type string;
          }
        }
      }
    }
    container zone {
      list security {
        // NCS patched for predictable order
        ordered-by user;
        key "id";
        leaf id {
          type string;
        }
        leaf description {
          type string;
        }
      }
    }
    container zone-pair {
      list security {
        // NCS patched for predictable order
        ordered-by user;
        key "id";
        leaf id {
          type string;
        }
        leaf source {
          type string;
        }
        leaf destination {
          type string;
        }
        leaf description {
          type string;
        }
        container service-policy {
          container type {
            leaf inspect {
              type string;
            }
          }
        }
      }
    }
    container aaa {
      leaf new-model {
        type empty;
      }
      container group {
        // NCS drop tailf-common:cli-diff-dependency statement
        container server {
          list tacacsplus {
            // NCS patched for predictable order
            ordered-by user;
            tailf:alt-name "tacacs+";
            key "name";
            leaf name {
              type string;
            }
            list server-private {
              // NCS patched for predictable order
              ordered-by user;
              tailf:cli-suppress-mode;
              key "name";
              leaf name {
                type ncs_compliance_template_host-type;
              }
              leaf timeout {
                type string;
              }
              container key {
                leaf encryption {
                  tailf:cli-drop-node-name;
                  type string;
                }
                leaf key {
                  tailf:cli-drop-node-name;
                  type string;
                }
              }
            }
            container ip {
              container tacacs {
                container source-interface {
                  // NCS drop tailf-common:cli-diff-dependency statement
                  uses ncs_compliance_template_interface-grouping;
                }
              }
            }
          }
          list radius {
            // NCS patched for predictable order
            ordered-by user;
            key "name";
            leaf name {
              type string;
            }
            container server {
              list name {
                // NCS patched for predictable order
                ordered-by user;
                tailf:cli-suppress-mode;
                key "name";
                leaf name {
                  type string;
                }
              }
              list direct {
                // NCS patched for predictable order
                ordered-by user;
                tailf:cli-drop-node-name;
                tailf:cli-suppress-mode;
                key "name";
                leaf name {
                  type string;
                }
                leaf auth-port {
                  type string;
                }
                leaf acct-port {
                  type string;
                }
              }
            }
            container ip {
              container radius {
                leaf source-interface {
                  type string;
                }
              }
              container vrf {
                leaf forwarding {
                  // NCS drop tailf-common:cli-diff-dependency statement
                  // NCS drop tailf-common:cli-diff-dependency statement
                  type string;
                }
              }
            }
          }
        }
      }
      container authentication {
        // NCS drop tailf-common:cli-diff-dependency statement
        container dot1x {
          list dot1x-list {
            // NCS patched for predictable order
            ordered-by user;
            tailf:cli-suppress-mode;
            key "name";
            leaf name {
              type string;
            }
            uses ncs_compliance_template_aaa-authentication-dot1x-grouping;
          }
          container default {
            uses ncs_compliance_template_aaa-authentication-dot1x-grouping;
          }
        }
        container enable {
          container default {
            leaf enable {
              type empty;
            }
            leaf group {
              type string;
            }
            leaf line {
              type empty;
            }
            leaf none {
              type empty;
            }
          }
        }
        list login {
          // NCS patched for predictable order
          ordered-by user;
          tailf:cli-suppress-mode;
          key "name";
          leaf name {
            type string;
          }
          leaf group {
            type string;
          }
          leaf local {
            type empty;
          }
          leaf none {
            type empty;
          }
        }
        list ppp {
          // NCS patched for predictable order
          ordered-by user;
          tailf:cli-suppress-mode;
          key "id";
          leaf id {
            type string;
          }
          container a1 {
            tailf:cli-drop-node-name;
            choice auth-choice {
              leaf if-needed {
                type empty;
              }
              leaf none {
                type empty;
              }
              leaf krb5 {
                type empty;
              }
              leaf local {
                type empty;
              }
              leaf local-case {
                type empty;
              }
              leaf group {
                type string;
              }
              leaf cache {
                type string;
              }
            }
          }
          container a2 {
            // NCS drop when statement
            tailf:cli-drop-node-name;
            choice auth-choice {
              leaf group {
                type string;
              }
              leaf cache {
                type string;
              }
              leaf none {
                type empty;
              }
              leaf krb5 {
                // NCS drop when statement
                type empty;
              }
              leaf local {
                // NCS drop when statement
                type empty;
              }
              leaf local-case {
                // NCS drop when statement
                type empty;
              }
            }
          }
          container a3 {
            // NCS drop when statement
            tailf:cli-drop-node-name;
            choice auth-choice {
              leaf group {
                type string;
              }
              leaf cache {
                type string;
              }
              leaf none {
                type empty;
              }
              leaf krb5 {
                // NCS drop when statement
                type empty;
              }
              leaf local {
                // NCS drop when statement
                type empty;
              }
              leaf local-case {
                // NCS drop when statement
                type empty;
              }
            }
          }
          container a4 {
            // NCS drop when statement
            tailf:cli-drop-node-name;
            choice auth-choice {
              leaf group {
                type string;
              }
              leaf cache {
                type string;
              }
              leaf none {
                type empty;
              }
              leaf krb5 {
                // NCS drop when statement
                type empty;
              }
              leaf local {
                // NCS drop when statement
                type empty;
              }
              leaf local-case {
                // NCS drop when statement
                type empty;
              }
            }
          }
        }
      }
      container authorization {
        // NCS drop tailf-common:cli-diff-dependency statement
        list commands {
          // NCS patched for predictable order
          ordered-by user;
          tailf:cli-suppress-mode;
          key "level list-name";
          leaf level {
            type string;
          }
          leaf list-name {
            type string;
          }
          leaf group {
            type string;
          }
          leaf if-authenticated {
            type empty;
          }
          leaf local {
            type empty;
          }
          leaf none {
            type empty;
          }
        }
        leaf console {
          type empty;
        }
        leaf config-commands {
          type empty;
        }
        list exec {
          // NCS patched for predictable order
          ordered-by user;
          tailf:cli-suppress-mode;
          key "name";
          leaf name {
            type string;
          }
          leaf group {
            type string;
          }
          leaf local {
            type empty;
          }
          leaf none {
            type empty;
          }
        }
        list eventmanager {
          // NCS patched for predictable order
          ordered-by user;
          tailf:cli-suppress-mode;
          key "name";
          leaf name {
            type string;
          }
          leaf group {
            type string;
          }
          leaf local {
            type empty;
          }
          leaf none {
            type empty;
          }
        }
        list network {
          // NCS patched for predictable order
          ordered-by user;
          tailf:cli-suppress-mode;
          key "id";
          leaf id {
            type string;
          }
          container a1 {
            tailf:cli-drop-node-name;
            choice auth-choice {
              leaf if-authenticated {
                type empty;
              }
              leaf none {
                type empty;
              }
              leaf local {
                type empty;
              }
              leaf group {
                type string;
              }
              leaf cache {
                type string;
              }
            }
          }
          container a2 {
            // NCS drop when statement
            tailf:cli-drop-node-name;
            choice auth-choice {
              leaf group {
                type string;
              }
              leaf cache {
                type string;
              }
              leaf if-authenticated {
                type empty;
              }
              leaf none {
                type empty;
              }
              leaf local {
                // NCS drop when statement
                type empty;
              }
            }
          }
          container a3 {
            // NCS drop when statement
            tailf:cli-drop-node-name;
            choice auth-choice {
              leaf group {
                type string;
              }
              leaf cache {
                type string;
              }
              leaf none {
                type empty;
              }
              leaf if-authenticated {
                type empty;
              }
              leaf local {
                // NCS drop when statement
                type empty;
              }
            }
          }
          container a4 {
            // NCS drop when statement
            tailf:cli-drop-node-name;
            choice auth-choice {
              leaf group {
                type string;
              }
              leaf cache {
                type string;
              }
              leaf none {
                type empty;
              }
              leaf if-authenticated {
                type empty;
              }
              leaf local {
                // NCS drop when statement
                type empty;
              }
            }
          }
        }
      }
      container accounting {
        // NCS drop tailf-common:cli-diff-dependency statement
        list commands {
          // NCS patched for predictable order
          ordered-by user;
          tailf:cli-suppress-mode;
          key "level list-name";
          leaf level {
            type string;
          }
          leaf list-name {
            type string;
          }
          leaf action-type {
            tailf:cli-drop-node-name;
            type string;
          }
          leaf broadcast {
            type empty;
          }
          leaf group {
            type string;
          }
        }
        list exec {
          // NCS patched for predictable order
          ordered-by user;
          key "name";
          leaf name {
            type string;
          }
          choice accounting-choice {
            leaf none {
              type empty;
            }
            container start-stop {
              leaf broadcast {
                type empty;
              }
              leaf group {
                type string;
              }
            }
            container stop-only {
              leaf broadcast {
                type empty;
              }
              leaf group {
                type string;
              }
            }
          }
        }
        list network {
          // NCS patched for predictable order
          ordered-by user;
          tailf:cli-suppress-mode;
          key "id";
          leaf id {
            type string;
          }
          choice network-choice {
            case a {
              leaf none {
                type empty;
              }
            }
            case b {
              leaf mode {
                tailf:cli-drop-node-name;
                type string;
              }
              leaf broadcast {
                type empty;
              }
              container a1 {
                tailf:cli-drop-node-name;
                leaf group {
                  type string;
                }
              }
              container a2 {
                tailf:cli-drop-node-name;
                leaf group {
                  type string;
                }
              }
              container a3 {
                tailf:cli-drop-node-name;
                leaf group {
                  type string;
                }
              }
              container a4 {
                tailf:cli-drop-node-name;
                leaf group {
                  type string;
                }
              }
            }
          }
        }
      }
      leaf session-id {
        // NCS drop tailf-common:cli-diff-dependency statement
        type string;
      }
    }
    container ethernet {
      list evc {
        // NCS patched for predictable order
        ordered-by user;
        key "name";
        leaf name {
          type string;
        }
      }
      container cfm {
        leaf ieee {
          type empty;
        }
        leaf global {
          type empty;
        }
        list domain {
          // NCS patched for predictable order
          ordered-by user;
          key "name";
          leaf name {
            type string;
          }
          leaf level {
            type string;
          }
          leaf service {
            type string;
          }
          leaf evc {
            type string;
          }
          leaf vlan {
            type string;
          }
        }
      }
    }
    list alarm-contact {
      // NCS patched for predictable order
      ordered-by user;
      tailf:cli-suppress-mode;
      key "name";
      leaf name {
        type string;
      }
      leaf description {
        type string;
      }
      leaf severity {
        type string;
      }
      leaf trigger {
        type string;
      }
    }
    container access-list {
      list access-list-standard-range {
        // NCS patched for predictable order
        ordered-by user;
        tailf:cli-drop-node-name;
        tailf:cli-suppress-mode;
        key "listnumber";
        leaf listnumber {
          tailf:cli-drop-node-name;
          type string;
        }
        list std-access-list-rule {
          // NCS patched for predictable order
          ordered-by user;
          tailf:cli-suppress-mode;
          tailf:cli-drop-node-name;
          key "rule";
          leaf rule {
            tailf:cli-drop-node-name;
            type string;
          }
        }
      }
      list access-list-extended-range {
        // NCS patched for predictable order
        ordered-by user;
        tailf:cli-drop-node-name;
        tailf:cli-suppress-mode;
        key "listnumber";
        leaf listnumber {
          tailf:cli-drop-node-name;
          type string;
        }
        list ext-access-list-rule {
          // NCS patched for predictable order
          ordered-by user;
          tailf:cli-suppress-mode;
          tailf:cli-drop-node-name;
          key "rule";
          leaf rule {
            tailf:cli-drop-node-name;
            type string;
          }
        }
      }
    }
    container crypto {
      container pki {
        list trustpoint {
          // NCS patched for predictable order
          ordered-by user;
          key "id";
          leaf id {
            type string;
          }
          container enrollment {
            leaf http-proxy {
              type string;
            }
            container mode {
              leaf ra {
                type empty;
              }
            }
            leaf profile {
              type string;
            }
            container retry {
              leaf count {
                type string;
              }
              leaf period {
                type string;
              }
            }
            leaf selfsigned {
              type empty;
            }
            container terminal {
              presence "true";
              leaf pem {
                type empty;
              }
            }
            leaf url {
              type string;
            }
          }
          leaf revocation-check {
            type string;
          }
          leaf rsakeypair {
            type string;
          }
          leaf subject-name {
            type string;
          }
        }
        container certificate {
          list chain {
            // NCS patched for predictable order
            ordered-by user;
            key "name";
            leaf name {
              type string;
            }
            list certificate {
              // NCS patched for predictable order
              ordered-by user;
              tailf:cli-suppress-mode;
              key "serial";
              leaf serial {
                type string;
              }
              leaf certtype {
                tailf:cli-drop-node-name;
                type string;
              }
              leaf cert {
                tailf:cli-drop-node-name;
                type string;
              }
            }
          }
        }
        container token {
          list token-name {
            // NCS patched for predictable order
            ordered-by user;
            tailf:cli-suppress-mode;
            tailf:cli-drop-node-name;
            key "name";
            leaf name {
              type string;
            }
            uses ncs_compliance_template_crypto-pki-token-grouping;
          }
        }
        container default {
          uses ncs_compliance_template_crypto-pki-token-grouping;
        }
      }
    }
    container mpls {
      container atm {
        leaf disable-headend-vc {
          type empty;
        }
      }
      leaf cos-map {
        type string;
      }
      container ip {
        leaf default-route {
          type empty;
        }
        container conf {
          tailf:cli-drop-node-name;
          leaf propagate-ttl {
            type string;
            // NCS drop default statement
          }
        }
        container conf-arg {
          tailf:cli-drop-node-name;
          container propagate-ttl {
            leaf forwarded {
              type string;
            }
          }
        }
        container ttl-expiration {
          leaf pop {
            type string;
          }
        }
      }
      container label {
        container atm {
          leaf disable-headend-vc {
            type empty;
          }
        }
        leaf protocol {
          type string;
          // NCS drop default statement
        }
        container range {
          leaf min {
            tailf:cli-drop-node-name;
            type string;
          }
          leaf max {
            tailf:cli-drop-node-name;
            type string;
          }
        }
      }
      container ldp {
        container enable {
          tailf:cli-drop-node-name;
          leaf advertise-labels {
            type string;
            // NCS drop default statement
          }
        }
        container enable2 {
          tailf:cli-drop-node-name;
          container advertise-labels {
            container for {
              leaf from {
                tailf:cli-drop-node-name;
                type string;
              }
              leaf to {
                type string;
              }
            }
            container interface {
              list FastEthernet {
                // NCS patched for predictable order
                ordered-by user;
                tailf:cli-suppress-mode;
                key "name";
                leaf name {
                  type string;
                }
              }
            }
            leaf oldstyle {
              type empty;
            }
          }
        }
        container atm {
          leaf control-mode {
            type string;
            // NCS drop default statement
          }
          leaf vc-merge {
            type string;
            // NCS drop default statement
          }
        }
        container backoff {
          leaf initial {
            tailf:cli-drop-node-name;
            type string;
          }
          leaf max {
            tailf:cli-drop-node-name;
            type string;
          }
        }
        container discovery {
          container hello {
            leaf holdtime {
              type string;
            }
            leaf interval {
              type string;
            }
          }
          container targeted-hello {
            container accept {
              presence "Accept targeted hellos";
              leaf from {
                type string;
              }
            }
            leaf holdtime {
              type string;
            }
            leaf interval {
              type string;
            }
          }
        }
        container explicit-null {
          presence "Advertise Explicit Null label in place of Implicit Null";
          leaf for {
            type string;
          }
          leaf to {
            type string;
          }
        }
        container graceful-restart {
          presence "Configure Graceful Restart timers";
          container timers {
            leaf forwarding-holding {
              type string;
            }
            leaf max-recovery {
              type string;
            }
            leaf neighbor-liveness {
              type string;
            }
          }
        }
        leaf holdtime {
          type string;
        }
        container logging {
          leaf neighbor-changes {
            type empty;
          }
        }
        leaf loop-detection {
          type empty;
        }
        leaf maxhops {
          type string;
        }
        list neighbor {
          // NCS patched for predictable order
          ordered-by user;
          tailf:cli-suppress-mode;
          key "address";
          leaf address {
            type string;
          }
          leaf implicit-withdraw {
            type empty;
          }
          container lables {
            leaf accept {
              type string;
            }
          }
          container password {
            leaf enctype {
              tailf:cli-drop-node-name;
              type string;
              // NCS drop default statement
            }
            leaf text {
              tailf:cli-drop-node-name;
              type string;
            }
          }
          container targeted {
            presence "Establish targeted session";
            leaf protocol {
              tailf:cli-drop-node-name;
              type string;
            }
          }
        }
        container request-labels {
          leaf for {
            type string;
          }
        }
        container router-id {
          leaf interface {
            tailf:cli-drop-node-name;
            type string;
          }
          leaf force {
            type empty;
          }
        }
      }
      container prefix-map {
        leaf nr {
          tailf:cli-drop-node-name;
          type string;
        }
        leaf access-list {
          type string;
        }
        leaf cos-map {
          type string;
        }
      }
      container traffic-eng {
        container auto-bw {
          container timers {
            presence "Enable auto-bw Timers Collection and Application";
            leaf frequency {
              type string;
            }
          }
        }
        container link-management {
          container timers {
            leaf bandwidth-hold {
              type string;
            }
            leaf periodic-flooding {
              type string;
            }
          }
        }
        container logging {
          container lsp {
            container path-errors {
              presence "Log LSP Path Error traps";
              leaf access-list {
                tailf:cli-drop-node-name;
                type ncs_compliance_template_access-list-type;
              }
            }
            container preemption {
              presence "Log LSP Preemption traps";
              leaf access-list {
                tailf:cli-drop-node-name;
                type ncs_compliance_template_access-list-type;
              }
            }
            container reservation-errors {
              presence "Log LSP Reservation Error traps";
              leaf access-list {
                tailf:cli-drop-node-name;
                type ncs_compliance_template_access-list-type;
              }
            }
            container setups {
              presence "Log LSP Establishment Traps";
              leaf access-list {
                tailf:cli-drop-node-name;
                type ncs_compliance_template_access-list-type;
              }
            }
            container teardowns {
              presence "Log LSP Teardown Traps";
              leaf access-list {
                tailf:cli-drop-node-name;
                type ncs_compliance_template_access-list-type;
              }
            }
          }
          container tunnel {
            container lsp-selection {
              presence "Log Tunnel LSP Selection traps";
              leaf access-list {
                tailf:cli-drop-node-name;
                type ncs_compliance_template_access-list-type;
              }
            }
            container path {
              container change {
                presence "Log Tunnel Path change traps";
                leaf access-list {
                  tailf:cli-drop-node-name;
                  type ncs_compliance_template_access-list-type;
                }
              }
            }
          }
        }
        container path-selection {
          leaf metric {
            type string;
          }
          container overload {
            container allow {
              leaf head {
                type empty;
              }
              leaf middle {
                type empty;
              }
              leaf tail {
                type empty;
              }
            }
          }
        }
        container reoptimize {
          container events {
            leaf link-up {
              type empty;
            }
          }
          container timers {
            container delay {
              leaf cleanup {
                type string;
              }
              leaf installation {
                type string;
              }
            }
            leaf frequency {
              type string;
            }
          }
        }
        container signalling {
          container advertise {
            container implicit-null {
              presence "Use MPLS encoding for Implicit-Null Label in signalling messages";
              leaf nr {
                tailf:cli-drop-node-name;
                type string;
              }
            }
          }
          container forwarding {
            leaf sync {
              type empty;
            }
          }
          container restart {
            container neighbors {
              presence "Identify signalling restart capable neighbors";
              leaf nr {
                tailf:cli-drop-node-name;
                type string;
              }
            }
          }
        }
        container topology {
          container holddown {
            leaf sigerr {
              type string;
            }
          }
        }
        leaf tunnels {
          type empty;
        }
      }
    }
    container router {
      list bgp {
        // NCS patched for predictable order
        ordered-by user;
        // NCS drop tailf-common:cli-diff-dependency statement
        // NCS drop tailf-common:cli-diff-dependency statement
        key "as-no";
        // NCS drop max-elements statement
        leaf as-no {
          type string;
        }
        uses ncs_compliance_template_bgp-address-family-grouping;
        container address-family {
          container no-vrf {
            tailf:cli-drop-node-name;
            list ipv4 {
              // NCS patched for predictable order
              ordered-by user;
              key "unicast-multicast";
              leaf unicast-multicast {
                type string;
              }
              uses ncs_compliance_template_bgp-address-family-grouping;
            }
          }
          container with-vrf {
            tailf:cli-drop-node-name;
            list ipv4 {
              // NCS patched for predictable order
              ordered-by user;
              tailf:cli-suppress-mode;
              key "unicast-multicast";
              leaf unicast-multicast {
                type string;
              }
              list vrf {
                // NCS patched for predictable order
                ordered-by user;
                // NCS drop tailf-common:cli-diff-dependency statement
                // NCS drop tailf-common:cli-diff-dependency statement
                key "name";
                leaf name {
                  type string;
                }
                uses ncs_compliance_template_bgp-address-family-grouping;
              }
            }
          }
          list ipv6 {
            // NCS patched for predictable order
            ordered-by user;
            tailf:cli-suppress-mode;
            key "unicast-multicast";
            leaf unicast-multicast {
              type string;
            }
            list vrf {
              // NCS patched for predictable order
              ordered-by user;
              // NCS drop tailf-common:cli-diff-dependency statement
              key "name";
              leaf name {
                type string;
              }
              uses ncs_compliance_template_bgp-address-family-grouping;
            }
            uses ncs_compliance_template_bgp-address-family-grouping;
          }
          list vpnv4 {
            // NCS patched for predictable order
            ordered-by user;
            key "unicast-multicast";
            leaf unicast-multicast {
              type string;
            }
            uses ncs_compliance_template_bgp-address-family-grouping;
          }
          list vpnv6 {
            // NCS patched for predictable order
            ordered-by user;
            key "unicast-multicast";
            leaf unicast-multicast {
              type string;
            }
            uses ncs_compliance_template_bgp-address-family-grouping;
          }
          list nsap {
            // NCS patched for predictable order
            ordered-by user;
            key "unicast-multicast";
            leaf unicast-multicast {
              type string;
            }
            uses ncs_compliance_template_bgp-address-family-grouping;
          }
        }
        container template {
          list peer-policy {
            // NCS patched for predictable order
            ordered-by user;
            key "name";
            leaf name {
              type string;
            }
          }
          list peer-session {
            // NCS patched for predictable order
            ordered-by user;
            key "name";
            leaf name {
              type string;
            }
          }
        }
      }
      list ospfv3 {
        // NCS patched for predictable order
        ordered-by user;
        key "id";
        leaf id {
          type string;
        }
        uses ncs_compliance_template_ospf-ospfv3-common-grouping;
        container address-family {
          container ipv4 {
            container unicast {
              uses ncs_compliance_template_ospf-ospfv3-common-grouping;
              uses ncs_compliance_template_ospf-ospfv3-common-address-family-grouping;
            }
          }
          container ipv6 {
            container unicast {
              uses ncs_compliance_template_ospf-ospfv3-common-grouping;
              uses ncs_compliance_template_ospf-ospfv3-common-address-family-grouping;
            }
          }
        }
      }
      list ospf {
        // NCS patched for predictable order
        ordered-by user;
        key "id";
        leaf id {
          type string;
        }
        list vrf {
          // NCS patched for predictable order
          ordered-by user;
          // NCS drop tailf-common:cli-diff-dependency statement
          // NCS drop tailf-common:cli-diff-dependency statement
          key "name";
          leaf name {
            type string;
          }
        }
        container non-vrf {
          tailf:cli-drop-node-name;
          uses ncs_compliance_template_ospf-ospfv3-common-grouping;
          uses ncs_compliance_template_ospf-ospfv3-common-address-family-grouping;
          container capability {
            leaf capability-type {
              tailf:cli-drop-node-name;
              type string;
            }
          }
          container compatible {
            leaf rfc1583 {
              type empty;
            }
          }
          uses ncs_compliance_template_distribute-list-grouping;
          container domain-id {
            choice domain-id-choice {
              leaf ip-format {
                tailf:cli-drop-node-name;
                type string;
              }
              container ip-format-secondary {
                tailf:cli-drop-node-name;
                leaf ip {
                  tailf:cli-drop-node-name;
                  type string;
                }
                leaf secondary {
                  type empty;
                }
              }
              leaf Null {
                type empty;
              }
              container type {
                leaf type-leaf {
                  tailf:cli-drop-node-name;
                  type string;
                }
                leaf value {
                  type string;
                }
              }
            }
          }
          leaf domain-tag {
            type string;
          }
          container ignore {
            container lsa {
              leaf mospf {
                type empty;
              }
            }
          }
          leaf ispf {
            type empty;
          }
          container limit {
            container retransmissions {
              leaf non-dc {
                type ncs_compliance_template_limit-dc-non-dc-type;
              }
              leaf dc {
                type ncs_compliance_template_limit-dc-non-dc-type;
              }
            }
          }
          container local-rib-criteria {
            leaf forwarding-address {
              type empty;
            }
            leaf inter-area-summary {
              type empty;
            }
            leaf nssa-translation {
              type empty;
            }
          }
          container max-metric {
            container router-lsa {
              presence "Maximum metric in self-originated router-LSAs";
              container external-lsa {
                presence "Override external-lsa metric with max-metric value";
                leaf metric {
                  tailf:cli-drop-node-name;
                  type string;
                }
              }
              leaf include-stub {
                type empty;
              }
              container on-startup {
                presence "Set maximum metric temporarily after reboot";
                choice time-wait-for-bgp-choice {
                  leaf time {
                    tailf:cli-drop-node-name;
                    type string;
                  }
                  leaf wait-for-bgp {
                    type empty;
                  }
                }
              }
              container summary-lsa {
                presence "Override summary-lsa metric with max-metric value";
                leaf metric {
                  tailf:cli-drop-node-name;
                  type string;
                }
              }
            }
          }
          container mpls {
            container ldp {
              container autoconfig {
                presence "Configure LDP automatic configuration";
                leaf area {
                  type ncs_compliance_template_ospf-area-type;
                }
              }
              container sync {
                presence "Configure LDP-IGP Synchronization";
              }
            }
            container traffic-eng {
              leaf multicast-intact {
                type empty;
              }
              leaf area {
                type ncs_compliance_template_ospf-area-type;
              }
              container interface {
                leaf name {
                  tailf:cli-drop-node-name;
                  type string;
                }
                leaf area {
                  type string;
                }
              }
              container mesh-group-container {
                tailf:cli-drop-node-name;
                leaf mesh-group {
                  type string;
                }
                leaf interface {
                  type string;
                }
                list area {
                  // NCS patched for predictable order
                  ordered-by user;
                  tailf:cli-suppress-mode;
                  key "id";
                  leaf id {
                    type ncs_compliance_template_ospf-area-type;
                  }
                }
              }
              container router-id {
                leaf interface {
                  type string;
                }
              }
            }
          }
          list neighbor {
            // NCS patched for predictable order
            ordered-by user;
            tailf:cli-suppress-mode;
            key "ip";
            leaf ip {
              type string;
            }
            container cost-database-filter-container {
              tailf:cli-drop-node-name;
              leaf cost {
                type string;
              }
              container database-filter {
                container all {
                  leaf out {
                    type empty;
                  }
                }
              }
            }
            container poll-interval-priority-container {
              tailf:cli-drop-node-name;
              leaf poll-interval {
                type string;
              }
              leaf priority {
                type string;
              }
            }
          }
          list network {
            // NCS patched for predictable order
            ordered-by user;
            tailf:cli-suppress-mode;
            key "ip mask";
            leaf ip {
              type string;
            }
            leaf mask {
              type string;
            }
            leaf area {
              type ncs_compliance_template_ospf-area-type;
            }
          }
          container nsf {
            container cisco {
              container helper {
                presence "helper support";
                leaf disable {
                  type empty;
                }
              }
            }
            container ietf {
              container helper {
                presence "helper support";
                leaf disable {
                  type empty;
                }
                leaf strict-lsa-checking {
                  type empty;
                }
              }
            }
          }
          leaf prefix-suppression {
            type empty;
          }
          container process-min-time {
            leaf percent {
              type string;
            }
          }
          container traffic-share {
            container min {
              leaf across-interface {
                type empty;
              }
            }
          }
          leaf shutdown {
            type string;
          }
          list summary-address {
            // NCS patched for predictable order
            ordered-by user;
            tailf:cli-suppress-mode;
            key "ip wildcard";
            leaf ip {
              type string;
            }
            leaf wildcard {
              type string;
            }
            choice tag-no-advertise-choice {
              leaf tag {
                type string;
              }
              leaf not-advertise {
                type empty;
              }
            }
          }
        }
      }
      container isis {
        presence "true";
        uses ncs_compliance_template_isis-main-grouping;
      }
      container isis-container {
        tailf:cli-drop-node-name;
        list isis {
          // NCS patched for predictable order
          ordered-by user;
          key "area-tag";
          leaf area-tag {
            type string;
          }
          uses ncs_compliance_template_isis-main-grouping;
        }
      }
      container rip {
        uses ncs_compliance_template_router-rip-grouping;
        container address-family {
          container ipv4 {
            container unicast {
              uses ncs_compliance_template_router-rip-grouping;
            }
            list vrf {
              // NCS patched for predictable order
              ordered-by user;
              // NCS drop tailf-common:cli-diff-dependency statement
              // NCS drop tailf-common:cli-diff-dependency statement
              key "name";
              leaf name {
                type string;
              }
              uses ncs_compliance_template_address-family-vrf-grouping;
            }
          }
        }
        container default {
          container address-family {
            container ipv4 {
              presence "true";
              leaf unicast {
                type empty;
              }
              list vrf {
                // NCS patched for predictable order
                ordered-by user;
                tailf:cli-suppress-mode;
                // NCS drop tailf-common:cli-diff-dependency statement
                // NCS drop tailf-common:cli-diff-dependency statement
                key "name";
                leaf name {
                  type string;
                }
              }
            }
          }
          uses ncs_compliance_template_default-router-rip-grouping;
          container default-information {
            leaf originate {
              type empty;
            }
          }
          leaf default-metric {
            type empty;
          }
          uses ncs_compliance_template_distance-grouping;
          uses ncs_compliance_template_distribute-list-grouping;
          leaf flash-update-threshold {
            type empty;
          }
          leaf input-queue {
            type empty;
          }
          uses ncs_compliance_template_offset-list-grouping;
          leaf output-delay {
            type empty;
          }
          uses ncs_compliance_template_passive-interface-grouping;
          container redistribute {
            uses ncs_compliance_template_default-redistribute-grouping;
          }
          container timers {
            leaf basic {
              type empty;
            }
          }
          container traffic-share {
            container min {
              leaf across-interfaces {
                type empty;
              }
            }
          }
          leaf version {
            type empty;
          }
        }
      }
    }
    container snmp {
      container ifmib {
        container ifindex {
          leaf persist {
            type empty;
          }
        }
        container ifalias {
          leaf long {
            type empty;
          }
        }
      }
      container mib {
        container bulkstat {
          list object-list {
            // NCS patched for predictable order
            ordered-by user;
            tailf:cli-suppress-mode;
            key "name";
            leaf name {
              type string;
            }
          }
        }
        leaf persist {
          type string;
        }
      }
    }
    container snmp-server {
      list community {
        // NCS patched for predictable order
        ordered-by user;
        tailf:cli-suppress-mode;
        key "name";
        leaf name {
          type string;
        }
        leaf view {
          type string;
        }
        choice access-choice {
          leaf RO {
            type empty;
          }
          leaf RW {
            type empty;
          }
        }
        choice access-list-choice {
          case ipv6 {
            leaf ipv6 {
              type string;
            }
          }
          case ipv4 {
            leaf access-list-name {
              tailf:cli-drop-node-name;
              type ncs_compliance_template_std-acl-type;
            }
          }
        }
      }
      leaf contact {
        type string;
      }
      container enable {
        choice enable-choice {
          case informs {
            leaf informs {
              type empty;
            }
          }
          case traps {
            container traps {
              leaf aaa_server {
                type empty;
              }
              container alarms {
                presence "true";
                leaf informational {
                  type empty;
                }
              }
              container atm {
                container pvc {
                  presence "true";
                  container extension {
                    leaf down {
                      type empty;
                    }
                    leaf up {
                      type empty;
                    }
                    leaf mibversion {
                      type string;
                    }
                    container oam {
                      container failure {
                        leaf loopback {
                          type empty;
                        }
                      }
                    }
                  }
                  leaf interval {
                    type string;
                  }
                  leaf fail-interval {
                    type string;
                  }
                }
                container subif {
                  presence "true";
                  leaf interval {
                    type string;
                  }
                  leaf count {
                    type string;
                  }
                }
              }
              leaf authenticate-fail {
                type empty;
              }
              container auth-framework {
                presence "true";
                leaf sec-violation {
                  type empty;
                }
              }
              leaf bfd {
                type empty;
              }
              leaf bgp {
                type empty;
              }
              container bridge {
                presence "true";
                leaf newroot {
                  type empty;
                }
                leaf topologychange {
                  type empty;
                }
              }
              leaf bstun {
                type empty;
              }
              container bulkstat {
                presence "true";
                leaf collection {
                  type empty;
                }
                leaf transfer {
                  type empty;
                }
              }
              container call-home {
                presence "true";
                leaf message-send-fail {
                  type empty;
                }
                leaf server-fail {
                  type empty;
                }
              }
              leaf c2900 {
                type empty;
              }
              container c6kxbar {
                presence "true";
                leaf intbus-crcexcd {
                  type empty;
                }
                leaf intbus-crcrcvrd {
                  type empty;
                }
                leaf swbus {
                  type empty;
                }
              }
              leaf casa {
                type empty;
              }
              leaf ccme {
                type empty;
              }
              container cef {
                leaf resource-failure {
                  type empty;
                }
                leaf peer-state-change {
                  type empty;
                }
                leaf peer-fib-state-change {
                  type empty;
                }
                leaf inconsistency {
                  type empty;
                }
              }
              leaf cluster {
                type empty;
              }
              leaf channel {
                type empty;
              }
              leaf chassis {
                type empty;
              }
              leaf cnpd {
                type empty;
              }
              leaf config {
                type empty;
              }
              leaf copy-config {
                type empty;
              }
              leaf config-copy {
                type empty;
              }
              leaf config-ctid {
                type empty;
              }
              container cpu {
                presence "true";
                leaf threshold {
                  type empty;
                }
              }
              container csg {
                presence "true";
                leaf agent {
                  type empty;
                }
                leaf database {
                  type empty;
                }
                leaf quota-server {
                  type empty;
                }
              }
              leaf dial {
                type empty;
              }
              leaf director {
                type empty;
              }
              leaf dlsw {
                type empty;
              }
              leaf deauthenticate {
                type empty;
              }
              leaf disassociate {
                type empty;
              }
              leaf dnis {
                type empty;
              }
              leaf dot11-qos {
                type empty;
              }
              container dot1x {
                leaf auth-fail-vlan {
                  type empty;
                }
                leaf guest-vlan {
                  type empty;
                }
                leaf no-auth-fail-vlan {
                  type empty;
                }
                leaf no-guest-vlan {
                  type empty;
                }
              }
              leaf ds0-busyout {
                type empty;
              }
              leaf ds1 {
                type empty;
              }
              leaf ds1-loopback {
                type empty;
              }
              leaf ds3 {
                type empty;
              }
              container dsp {
                presence "true";
                leaf card-status {
                  type empty;
                }
                leaf oper-state {
                  type empty;
                }
              }
              leaf eigrp {
                type empty;
              }
              container energywise {
                presence "true";
                leaf event-occured {
                  type empty;
                }
                leaf level-change {
                  type empty;
                }
                leaf neighbor-added {
                  type empty;
                }
                leaf neighbor-deleted {
                  type empty;
                }
              }
              leaf entity {
                type empty;
              }
              container entity-diag {
                presence "true";
                leaf boot-up-fail {
                  type empty;
                }
                leaf hm-test-recover {
                  type empty;
                }
                leaf hm-thresh-reached {
                  type empty;
                }
                leaf scheduled-test-fail {
                  type empty;
                }
              }
              container envmon {
                presence "true";
                leaf fan {
                  type empty;
                }
                leaf shutdown {
                  type empty;
                }
                leaf supply {
                  type empty;
                }
                leaf temperature {
                  type empty;
                }
                leaf status {
                  type empty;
                }
              }
              container errdisable {
                presence "true";
                leaf notification-rate {
                  type string;
                }
              }
              leaf ether-oam {
                type empty;
              }
              container ethernet {
                container cfm {
                  leaf alarm {
                    type empty;
                  }
                  container cc {
                    presence "true";
                    leaf config {
                      type empty;
                    }
                    leaf cross-connect {
                      type empty;
                    }
                    leaf loop {
                      type empty;
                    }
                    leaf mep-down {
                      type empty;
                    }
                    leaf mep-up {
                      type empty;
                    }
                  }
                  container crosscheck {
                    presence "true";
                    leaf mep-missing {
                      type empty;
                    }
                    leaf mep-unknown {
                      type empty;
                    }
                    leaf service-up {
                      type empty;
                    }
                  }
                }
                container evc {
                  presence "true";
                  leaf create {
                    type empty;
                  }
                  leaf delete {
                    type empty;
                  }
                  leaf status {
                    type empty;
                  }
                }
              }
              leaf event-manager {
                type empty;
              }
              container firewall {
                presence "true";
                leaf serverstatus {
                  type empty;
                }
              }
              container flash {
                presence "true";
                leaf insertion {
                  type empty;
                }
                leaf removal {
                  type empty;
                }
              }
              leaf flowmon {
                type empty;
              }
              container flex-links {
                presence "true";
                leaf status {
                  type empty;
                }
              }
              container frame-relay {
                presence "true";
                container multilink {
                  leaf bundle-mismatch {
                    type empty;
                  }
                }
                container subif {
                  presence "true";
                }
              }
              leaf fru-ctrl {
                type empty;
              }
              leaf gatekeeper {
                type empty;
              }
              leaf hsrp {
                type empty;
              }
              leaf icsudsu {
                type empty;
              }
              leaf ima {
                type empty;
              }
              leaf ipmobile {
                type empty;
              }
              leaf ipmulticast {
                type empty;
              }
              container ipsec {
                container cryptomap {
                  leaf add {
                    type empty;
                  }
                  leaf attach {
                    type empty;
                  }
                  leaf delete {
                    type empty;
                  }
                  leaf detach {
                    type empty;
                  }
                }
                container tunnel {
                  leaf start {
                    type empty;
                  }
                  leaf stop {
                    type empty;
                  }
                }
                leaf too-many-sas {
                  type empty;
                }
              }
              container isakmp {
                container policy {
                  leaf add {
                    type empty;
                  }
                  leaf delete {
                    type empty;
                  }
                }
                container tunnel {
                  leaf start {
                    type empty;
                  }
                  leaf stop {
                    type empty;
                  }
                }
              }
              container isdn {
                presence "true";
                leaf call-information {
                  type empty;
                }
                leaf chan-not-avail {
                  type empty;
                }
                leaf ietf {
                  type empty;
                }
                leaf layer2 {
                  type empty;
                }
              }
              leaf ipsla {
                type empty;
              }
              leaf isis {
                type empty;
              }
              container l2tc {
                presence "true";
                leaf sys-threshold {
                  type empty;
                }
                leaf threshold {
                  type empty;
                }
              }
              container l2tun {
                leaf session {
                  type empty;
                }
                container pseudowire {
                  leaf status {
                    type empty;
                  }
                }
              }
              leaf license {
                type empty;
              }
              container mac-notification {
                presence "true";
                container change {
                  presence "true";
                  leaf move {
                    type empty;
                  }
                  leaf threshold {
                    type empty;
                  }
                }
              }
              container mac-notification2 {
                tailf:alt-name "MAC-Notification";
                presence "true";
                leaf move {
                  type empty;
                }
                leaf threshold {
                  type empty;
                }
              }
              container memory {
                leaf bufferpeak {
                  type empty;
                }
              }
              leaf module {
                type empty;
              }
              container mpls {
                presence "true";
                container traffic-eng {
                  presence "true";
                }
                container fast-reroute {
                  presence "true";
                  leaf protected {
                    type empty;
                  }
                }
                container rfc {
                  presence "true";
                  leaf ldp {
                    type empty;
                  }
                }
                container ldp {
                  presence "true";
                  leaf pv-limit {
                    type empty;
                  }
                  leaf session-down {
                    type empty;
                  }
                  leaf session-up {
                    type empty;
                  }
                  leaf threshold {
                    type empty;
                  }
                }
                leaf vpn {
                  type empty;
                }
              }
              leaf msdp {
                type empty;
              }
              leaf mvpn {
                type empty;
              }
              container nhrp {
                presence "true";
                container nhs {
                  presence "true";
                }
                container nhc {
                  presence "true";
                }
                container nhp {
                  presence "true";
                }
                container quota-exceeded {
                  presence "true";
                }
              }
              container ospf {
                container state-change {
                  presence "true";
                  leaf if-state-change {
                    type empty;
                  }
                  leaf neighbor-state-change {
                    type empty;
                  }
                  leaf virtif-state-change {
                    type empty;
                  }
                  leaf virtneighbor-state-change {
                    type empty;
                  }
                }
                container errors {
                  presence "true";
                }
                container retransmit {
                  presence "true";
                  leaf packets {
                    type empty;
                  }
                  leaf virt-packets {
                    type empty;
                  }
                }
                container lsa {
                  presence "true";
                  leaf lsa-maxage {
                    type empty;
                  }
                  leaf lsa-originate {
                    type empty;
                  }
                }
                container cisco-specific {
                  presence "true";
                  container state-change {
                    presence "true";
                    leaf nssa-trans-change {
                      type empty;
                    }
                    container shamlink {
                      presence "true";
                      leaf interface {
                        type empty;
                      }
                      leaf interface-old {
                        type empty;
                      }
                      leaf neighbor {
                        type empty;
                      }
                    }
                  }
                  container errors {
                    presence "true";
                  }
                  container errdisable {
                    presence "true";
                    leaf notification-rate {
                      type string;
                    }
                  }
                  container retransmit {
                    presence "true";
                  }
                  container lsa {
                    presence "true";
                    leaf lsa-maxage {
                      type empty;
                    }
                    leaf lsa-originate {
                      type empty;
                    }
                  }
                }
              }
              container pim {
                presence "true";
                leaf invalid-pim-message {
                  type empty;
                }
                leaf neighbor-change {
                  type empty;
                }
                leaf rp-mapping-change {
                  type empty;
                }
              }
              container port-security {
                presence "true";
                leaf trap-rate {
                  type string;
                }
              }
              container power-ethernet {
                leaf group {
                  type string;
                }
                leaf police {
                  type empty;
                }
              }
              leaf pppoe {
                type empty;
              }
              container pw {
                presence "true";
                leaf vc {
                  type empty;
                }
              }
              leaf rep {
                type empty;
              }
              leaf resource-policy {
                type empty;
              }
              leaf rf {
                type empty;
              }
              leaf rogue-ap {
                type empty;
              }
              leaf rsvp {
                type empty;
              }
              leaf rtr {
                type empty;
              }
              container slb {
                presence "true";
                leaf csrp {
                  type empty;
                }
                leaf real {
                  type empty;
                }
                leaf virtual {
                  type empty;
                }
              }
              container snmp {
                leaf authentication {
                  type empty;
                }
                leaf coldstart {
                  type empty;
                }
                leaf linkdown {
                  type empty;
                }
                leaf linkup {
                  type empty;
                }
                leaf warmstart {
                  type empty;
                }
              }
              leaf sonet {
                type empty;
              }
              leaf srst {
                type empty;
              }
              leaf srp {
                type empty;
              }
              container stackwise {
                presence "true";
                leaf GLS {
                  type empty;
                }
                leaf ILS {
                  type empty;
                }
                leaf SRLS {
                  type empty;
                }
                leaf insufficient-power {
                  type empty;
                }
                leaf invalid-input-current {
                  type empty;
                }
                leaf invalid-output-current {
                  type empty;
                }
                leaf member-removed {
                  type empty;
                }
                leaf member-upgrade-notification {
                  type empty;
                }
                leaf new-master {
                  type empty;
                }
                leaf new-member {
                  type empty;
                }
                leaf port-change {
                  type empty;
                }
                leaf power-budget-warning {
                  type empty;
                }
                leaf power-invalid-topology {
                  type empty;
                }
                leaf power-link-status-changed {
                  type empty;
                }
                leaf power-oper-status-changed {
                  type empty;
                }
                leaf power-priority-conflict {
                  type empty;
                }
                leaf power-version-mismatch {
                  type empty;
                }
                leaf ring-redundant {
                  type empty;
                }
                leaf stack-mismatch {
                  type empty;
                }
                leaf unbalanced-power-supplies {
                  type empty;
                }
                leaf under-budget {
                  type empty;
                }
                leaf under-voltage {
                  type empty;
                }
              }
              container stpx {
                presence "true";
                leaf inconsistency {
                  type empty;
                }
                leaf root-inconsistency {
                  type empty;
                }
                leaf loop-inconsistency {
                  type empty;
                }
              }
              leaf stun {
                type empty;
              }
              leaf switch-over {
                type empty;
              }
              leaf syslog {
                type empty;
              }
              container transceiver {
                leaf all {
                  type empty;
                }
              }
              leaf tty {
                type empty;
              }
              container udld {
                presence "true";
                leaf link-fail-rpt {
                  type empty;
                }
                leaf status-change {
                  type empty;
                }
              }
              leaf vlancreate {
                type empty;
              }
              leaf vlandelete {
                type empty;
              }
              leaf vlan-mac-limit {
                type empty;
              }
              leaf vlan-membership {
                type empty;
              }
              leaf voice {
                type empty;
              }
              container vrfmib {
                leaf vrf-up {
                  type empty;
                }
                leaf vrf-down {
                  type empty;
                }
                leaf vnet-trunk-up {
                  type empty;
                }
                leaf vnet-trunk-down {
                  type empty;
                }
              }
              leaf vrrp {
                type empty;
              }
              leaf vsimaster {
                type empty;
              }
              container vstack {
                presence "true";
                leaf addition {
                  type empty;
                }
                leaf failure {
                  type empty;
                }
                leaf lost {
                  type empty;
                }
                leaf operation {
                  type empty;
                }
              }
              leaf vtp {
                type empty;
              }
              leaf wlan-wep {
                type empty;
              }
              leaf xgcp {
                type empty;
              }
            }
          }
        }
      }
      container engineID {
        leaf local {
          type string;
        }
        container remote;
      }
      list group {
        // NCS patched for predictable order
        ordered-by user;
        tailf:cli-suppress-mode;
        key "id";
        leaf id {
          type string;
        }
        choice security-model {
          container v1;
          container v2c;
          container v3 {
            leaf security-level {
              tailf:cli-drop-node-name;
              type string;
            }
            leaf context {
              type string;
            }
            leaf match {
              type string;
            }
            leaf read {
              type string;
            }
            leaf write {
              type string;
            }
            leaf notify {
              type string;
            }
            leaf access {
              type string;
            }
          }
        }
      }
      list host {
        // NCS patched for predictable order
        ordered-by user;
        tailf:cli-suppress-mode;
        key "ip-address";
        leaf ip-address {
          type ncs_compliance_template_host-type;
        }
        leaf vrf {
          // NCS drop tailf-common:cli-diff-dependency statement
          // NCS drop tailf-common:cli-diff-dependency statement
          type string;
        }
        choice informs-traps-choice {
          leaf informs {
            type empty;
          }
          leaf traps {
            type empty;
          }
          // NCS drop default statement
        }
        container version {
          leaf version {
            tailf:cli-drop-node-name;
            type string;
          }
          leaf security-level {
            tailf:cli-drop-node-name;
            // NCS drop when statement
            type string;
          }
        }
        list community-string {
          // NCS patched for predictable order
          ordered-by user;
          tailf:cli-drop-node-name;
          tailf:cli-suppress-mode;
          key "name";
          leaf name {
            type string;
          }
          leaf aaa_server {
            type empty;
          }
          leaf alarms {
            type empty;
          }
          leaf atm {
            type empty;
          }
          leaf bfd {
            type empty;
          }
          leaf bgp {
            type empty;
          }
          leaf bstun {
            type empty;
          }
          leaf bulkstat {
            type empty;
          }
          leaf call-home {
            type empty;
          }
          leaf casa {
            type empty;
          }
          leaf cef {
            type empty;
          }
          leaf cnpd {
            type empty;
          }
          leaf config {
            type empty;
          }
          leaf config-copy {
            type empty;
          }
          leaf config-ctid {
            type empty;
          }
          leaf cpu {
            type empty;
          }
          leaf dhcp {
            type empty;
          }
          leaf dlsw {
            type empty;
          }
          leaf ds1 {
            type empty;
          }
          leaf dsp {
            type empty;
          }
          leaf dspu {
            type empty;
          }
          leaf eigrp {
            type empty;
          }
          leaf entity {
            type empty;
          }
          leaf entity-diag {
            type empty;
          }
          leaf entity-qfp {
            type empty;
          }
          leaf entity-state {
            type empty;
          }
          leaf ethernet-cfm {
            type empty;
          }
          leaf evc {
            type empty;
          }
          leaf event-manager {
            type empty;
          }
          leaf firewall {
            type empty;
          }
          leaf flash {
            type empty;
          }
          leaf flowmon {
            type empty;
          }
          leaf frame-relay {
            type empty;
          }
          leaf fru-ctrl {
            type empty;
          }
          leaf gdoi {
            type empty;
          }
          leaf hsrp {
            type empty;
          }
          leaf iplocalpool {
            type empty;
          }
          leaf ipmulticast {
            type empty;
          }
          leaf ipsec {
            type empty;
          }
          leaf ipsla {
            type empty;
          }
          leaf isakmp {
            type empty;
          }
          leaf isg-mib {
            type empty;
          }
          leaf isis {
            type empty;
          }
          leaf l2tun-pseudowire-status {
            type empty;
          }
          leaf l2tun-session {
            type empty;
          }
          leaf license {
            type empty;
          }
          leaf memory {
            type empty;
          }
          leaf mpls-fast-reroute {
            type empty;
          }
          leaf mpls-ldp {
            type empty;
          }
          leaf mpls-traffic-eng {
            type empty;
          }
          leaf mpls-vpn {
            type empty;
          }
          leaf msdp {
            type empty;
          }
          leaf mvpn {
            type empty;
          }
          leaf nhrp {
            type empty;
          }
          leaf ospf {
            type empty;
          }
          leaf ospfv3 {
            type empty;
          }
          leaf pfr {
            type empty;
          }
          leaf pim {
            type empty;
          }
          leaf pw-vc {
            type empty;
          }
          leaf resource-policy {
            type empty;
          }
          leaf rf {
            type empty;
          }
          leaf rsrb {
            type empty;
          }
          leaf rsvp {
            type empty;
          }
          leaf sdlc {
            type empty;
          }
          leaf sdllc {
            type empty;
          }
          leaf snmp {
            type empty;
          }
          leaf sonet {
            type empty;
          }
          leaf srp {
            type empty;
          }
          leaf stun {
            type empty;
          }
          leaf syslog {
            type empty;
          }
          leaf trustsec-sxp {
            type empty;
          }
          leaf tty {
            type empty;
          }
          leaf udp-port {
            type empty;
          }
          leaf voice {
            type empty;
          }
          leaf vrfmib {
            type empty;
          }
          leaf vrrp {
            type empty;
          }
          leaf x25 {
            type empty;
          }
        }
      }
      container ip {
        leaf precedence {
          type string;
        }
      }
      container ifindex {
        leaf persist {
          type empty;
        }
      }
      leaf location {
        type string;
      }
      container manager {
        presence "true";
        leaf session-timeout {
          type string;
        }
      }
      leaf queue-length {
        type string;
      }
      container source-interface {
        container informs {
          // NCS drop tailf-common:cli-diff-dependency statement
          uses ncs_compliance_template_interface-grouping;
        }
        container traps {
          // NCS drop tailf-common:cli-diff-dependency statement
          uses ncs_compliance_template_interface-grouping;
        }
      }
      container trap {
        leaf timeout {
          type string;
        }
      }
      container trap-source {
        // NCS drop tailf-common:cli-diff-dependency statement
        uses ncs_compliance_template_interface-grouping;
      }
      list view {
        // NCS patched for predictable order
        ordered-by user;
        tailf:cli-suppress-mode;
        key "name mib";
        leaf name {
          type string;
        }
        leaf mib {
          type string;
        }
        leaf inc-exl {
          tailf:cli-drop-node-name;
          type string;
        }
      }
    }
    container dot11 {
      leaf syslog {
        type empty;
      }
    }
    container license {
      container udi {
        leaf pid {
          type string;
        }
        leaf sn {
          type string;
        }
      }
      container boot {
        container level {
          container ipbase {
            presence "true";
            leaf switch {
              type string;
            }
          }
          container ipservices {
            presence "true";
            leaf switch {
              type empty;
            }
          }
          container lanbase {
            presence "true";
            leaf switch {
              type empty;
            }
          }
        }
      }
    }
    list voice-card {
      // NCS patched for predictable order
      ordered-by user;
      key "slot";
      leaf slot {
        type string;
      }
    }
    container card {
      leaf type {
        type string;
      }
      leaf slot {
        tailf:cli-drop-node-name;
        type string;
      }
      leaf bay {
        tailf:cli-drop-node-name;
        type string;
      }
    }
    container event {
      container manager {
        list applet {
          // NCS patched for predictable order
          ordered-by user;
          key "name";
          leaf name {
            type string;
          }
          leaf authorization {
            type string;
          }
          leaf class {
            type string;
          }
          leaf trap {
            type empty;
          }
          container event {
            container snmp-notification {
              leaf oid {
                type string;
              }
              leaf oid-val {
                type string;
              }
              leaf op {
                type ncs_compliance_template_operator-type;
              }
              leaf src-ip-address {
                type string;
              }
              leaf dest-ip-address {
                type string;
              }
            }
            container syslog {
              leaf pattern {
                type string;
              }
            }
          }
          list action {
            // NCS patched for predictable order
            ordered-by user;
            tailf:cli-suppress-mode;
            key "name";
            leaf name {
              type string;
            }
            container if {
              leaf string-op-1 {
                tailf:cli-drop-node-name;
                type string;
              }
              leaf keyword {
                tailf:cli-drop-node-name;
                type ncs_compliance_template_operator-type;
              }
              leaf string-op-2 {
                tailf:cli-drop-node-name;
                type string;
              }
              leaf goto {
                type string;
              }
            }
            container info {
              container type {
                container snmp {
                  container var {
                    leaf variable-name {
                      tailf:cli-drop-node-name;
                      type string;
                    }
                    leaf oid {
                      type string;
                    }
                    leaf oid-type {
                      tailf:cli-drop-node-name;
                      type string;
                    }
                    leaf oid-type-value {
                      tailf:cli-drop-node-name;
                      type string;
                    }
                  }
                  container trap {
                    leaf enterprise-oid {
                      type string;
                    }
                    leaf generic-trapnum {
                      type string;
                    }
                    leaf specific-trapnum {
                      type string;
                    }
                    leaf trap-oid {
                      type string;
                    }
                    leaf trap-var {
                      type string;
                    }
                  }
                }
              }
            }
            leaf end {
              type empty;
            }
            container regexp {
              leaf string-pattern {
                tailf:cli-drop-node-name;
                type string;
              }
              leaf string-input {
                tailf:cli-drop-node-name;
                type string;
              }
              leaf string-match {
                tailf:cli-drop-node-name;
                type string;
              }
              leaf string-submatch1 {
                tailf:cli-drop-node-name;
                type string;
              }
              leaf string-submatch2 {
                tailf:cli-drop-node-name;
                type string;
              }
              leaf string-submatch3 {
                tailf:cli-drop-node-name;
                type string;
              }
            }
            container snmp-trap {
              presence "true";
              leaf intdata1 {
                type string;
              }
              leaf intdata2 {
                type string;
              }
              leaf strdata {
                type string;
              }
            }
            container string {
              leaf trim {
                type string;
              }
            }
            container syslog {
              leaf facility {
                type string;
              }
              leaf msg {
                type string;
              }
              leaf priority {
                type ncs_compliance_template_logging-level-type;
              }
            }
          }
          leaf description {
            type string;
          }
          container trigger;
        }
      }
    }
    leaf disable-eadi {
      type empty;
    }
    container memory-size {
      leaf iomem {
        type string;
      }
    }
    container transceiver {
      container type {
        container all {
          container monitoring {
            presence "true";
            leaf interval {
              type string;
            }
          }
        }
      }
    }
  }
  augment "/ncs:compliance/ncs:template/ncs:ned-id/ncs:config/router/rip/default/distribute-list/accesslist" {
    leaf id {
      tailf:cli-drop-node-name;
      // NCS drop mandatory statement
      type ncs_compliance_template_default-access-list-id-type;
    }
  }
  augment "/ncs:devices/ncs:template/ncs:ned-id/ncs:config/router/rip/default/distribute-list/accesslist" {
    leaf id {
      tailf:cli-drop-node-name;
      // NCS drop mandatory statement
      type ncs_template_default-access-list-id-type;
    }
  }
  augment "/ncs:devices/ncs:device/ncs:config/router/rip/default/distribute-list/accesslist" {
    leaf id {
      tailf:ncs-device-type "cli-ned";
      tailf:display-when "not(../../../../../../../ncs:module) or ../../../../../../../ncs:module[ncs:name='tailf-ned-cisco-ios']";
      tailf:cli-drop-node-name;
      tailf:cli-prefix-key;
      mandatory true;
      tailf:cli-disallow-value "prefix|gateway";
      type default-access-list-id-type;
    }
  }
  augment "/ncs:compliance/ncs:template/ncs:ned-id/ncs:config/router/rip/distribute-list/accesslist" {
    leaf id {
      tailf:cli-drop-node-name;
      // NCS drop mandatory statement
      type ncs_compliance_template_access-list-id-type;
    }
  }
  augment "/ncs:devices/ncs:template/ncs:ned-id/ncs:config/router/rip/distribute-list/accesslist" {
    leaf id {
      tailf:cli-drop-node-name;
      // NCS drop mandatory statement
      type ncs_template_access-list-id-type;
    }
  }
  augment "/ncs:devices/ncs:device/ncs:config/router/rip/distribute-list/accesslist" {
    leaf id {
      tailf:ncs-device-type "cli-ned";
      tailf:display-when "not(../../../../../../ncs:module) or ../../../../../../ncs:module[ncs:name='tailf-ned-cisco-ios']";
      tailf:cli-drop-node-name;
      tailf:cli-prefix-key;
      mandatory true;
      tailf:cli-disallow-value "prefix|gateway";
      type access-list-id-type;
    }
  }
  augment "/ncs:compliance/ncs:template/ncs:ned-id/ncs:config/router/rip/default/distribute-list/accesslist-ifname" {
    leaf id {
      tailf:cli-drop-node-name;
      // NCS drop mandatory statement
      type ncs_compliance_template_default-access-list-id-type;
    }
  }
  augment "/ncs:devices/ncs:template/ncs:ned-id/ncs:config/router/rip/default/distribute-list/accesslist-ifname" {
    leaf id {
      tailf:cli-drop-node-name;
      // NCS drop mandatory statement
      type ncs_template_default-access-list-id-type;
    }
  }
  augment "/ncs:devices/ncs:device/ncs:config/router/rip/default/distribute-list/accesslist-ifname" {
    leaf id {
      tailf:ncs-device-type "cli-ned";
      tailf:display-when "not(../../../../../../../ncs:module) or ../../../../../../../ncs:module[ncs:name='tailf-ned-cisco-ios']";
      tailf:cli-drop-node-name;
      tailf:cli-prefix-key;
      mandatory true;
      tailf:cli-disallow-value "prefix|gateway";
      type default-access-list-id-type;
    }
  }
  augment "/ncs:compliance/ncs:template/ncs:ned-id/ncs:config/router/rip/distribute-list/accesslist-ifname" {
    leaf id {
      tailf:cli-drop-node-name;
      // NCS drop mandatory statement
      type ncs_compliance_template_access-list-id-type;
    }
  }
  augment "/ncs:devices/ncs:template/ncs:ned-id/ncs:config/router/rip/distribute-list/accesslist-ifname" {
    leaf id {
      tailf:cli-drop-node-name;
      // NCS drop mandatory statement
      type ncs_template_access-list-id-type;
    }
  }
  augment "/ncs:devices/ncs:device/ncs:config/router/rip/distribute-list/accesslist-ifname" {
    leaf id {
      tailf:ncs-device-type "cli-ned";
      tailf:display-when "not(../../../../../../ncs:module) or ../../../../../../ncs:module[ncs:name='tailf-ned-cisco-ios']";
      tailf:cli-drop-node-name;
      tailf:cli-prefix-key;
      mandatory true;
      tailf:cli-disallow-value "prefix|gateway";
      type access-list-id-type;
    }
  }
  augment "/ncs:compliance/ncs:template/ncs:ned-id/ncs:config/router/rip/default/distance/distance-list" {
    leaf access-list {
      tailf:cli-drop-node-name;
      type ncs_compliance_template_default-access-list-standard-id-type;
    }
  }
  augment "/ncs:devices/ncs:template/ncs:ned-id/ncs:config/router/rip/default/distance/distance-list" {
    leaf access-list {
      tailf:cli-drop-node-name;
      type ncs_template_default-access-list-standard-id-type;
    }
  }
  augment "/ncs:devices/ncs:device/ncs:config/router/rip/default/distance/distance-list" {
    leaf access-list {
      tailf:ncs-device-type "cli-ned";
      tailf:display-when "not(../../../../../../../ncs:module) or ../../../../../../../ncs:module[ncs:name='tailf-ned-cisco-ios']";
      tailf:cli-drop-node-name;
      type default-access-list-standard-id-type;
    }
  }
  augment "/ncs:compliance/ncs:template/ncs:ned-id/ncs:config/router/rip/distance/distance-list" {
    leaf access-list {
      tailf:cli-drop-node-name;
      type ncs_compliance_template_access-list-standard-id-type;
    }
  }
  augment "/ncs:devices/ncs:template/ncs:ned-id/ncs:config/router/rip/distance/distance-list" {
    leaf access-list {
      tailf:cli-drop-node-name;
      type ncs_template_access-list-standard-id-type;
    }
  }
  augment "/ncs:devices/ncs:device/ncs:config/router/rip/distance/distance-list" {
    leaf access-list {
      tailf:ncs-device-type "cli-ned";
      tailf:display-when "not(../../../../../../ncs:module) or ../../../../../../ncs:module[ncs:name='tailf-ned-cisco-ios']";
      tailf:cli-drop-node-name;
      type access-list-standard-id-type;
    }
  }
  augment "/ncs:compliance/ncs:template/ncs:ned-id/ncs:config/router/rip/default/offset-list" {
    leaf id {
      tailf:cli-drop-node-name;
      // NCS drop mandatory statement
      type ncs_compliance_template_default-offset-list-id-type;
    }
  }
  augment "/ncs:devices/ncs:template/ncs:ned-id/ncs:config/router/rip/default/offset-list" {
    leaf id {
      tailf:cli-drop-node-name;
      // NCS drop mandatory statement
      type ncs_template_default-offset-list-id-type;
    }
  }
  augment "/ncs:devices/ncs:device/ncs:config/router/rip/default/offset-list" {
    leaf id {
      tailf:ncs-device-type "cli-ned";
      tailf:display-when "not(../../../../../../ncs:module) or ../../../../../../ncs:module[ncs:name='tailf-ned-cisco-ios']";
      tailf:cli-incomplete-command;
      tailf:cli-drop-node-name;
      tailf:cli-prefix-key {
        tailf:cli-before-key 1;
      }
      mandatory true;
      tailf:cli-disallow-value "in|out";
      type default-offset-list-id-type;
    }
  }
  augment "/ncs:compliance/ncs:template/ncs:ned-id/ncs:config/router/rip/offset-list" {
    leaf id {
      tailf:cli-drop-node-name;
      // NCS drop mandatory statement
      type ncs_compliance_template_offset-list-id-type;
    }
  }
  augment "/ncs:devices/ncs:template/ncs:ned-id/ncs:config/router/rip/offset-list" {
    leaf id {
      tailf:cli-drop-node-name;
      // NCS drop mandatory statement
      type ncs_template_offset-list-id-type;
    }
  }
  augment "/ncs:devices/ncs:device/ncs:config/router/rip/offset-list" {
    leaf id {
      tailf:ncs-device-type "cli-ned";
      tailf:display-when "not(../../../../../ncs:module) or ../../../../../ncs:module[ncs:name='tailf-ned-cisco-ios']";
      tailf:cli-incomplete-command;
      tailf:cli-drop-node-name;
      tailf:cli-prefix-key {
        tailf:cli-before-key 1;
      }
      mandatory true;
      tailf:cli-disallow-value "in|out";
      type offset-list-id-type;
    }
  }
}
