submodule tailf-ned-cisco-nx-router {
  // Generated by yanger -t ncs
  tailf:mount-id "cisco-nx-cli-3.0:cisco-nx-cli-3.0";

  belongs-to tailf-ned-cisco-nx {
    prefix nx;
  }

  import tailf-common {
    prefix tailf;
  }
  import tailf-ncs {
    prefix ncs;
  }

  augment "/ncs:devices/ncs:device/ncs:config" {
    container router {
      tailf:ncs-device-type "cli-ned";
      tailf:display-when "not(../../ncs:module) or ../../ncs:module[ncs:name='tailf-ned-cisco-nx']";
      tailf:info
        "Enable a routing process";
    }
  }
  augment "/ncs:devices/ncs:template/ncs:ned-id/ncs:config" {
    container router;
  }
  augment "/ncs:compliance/ncs:template/ncs:ned-id/ncs:config" {
    container router;
  }
}
