module common_config {

  namespace "http://example.com/common_config";
  prefix common_config;

  import ietf-inet-types {
    prefix inet;
  }
  import tailf-common {
    prefix tailf;
  }
  import tailf-ncs {
    prefix ncs;
  }

  description
    "Bla bla...";

  revision 2016-01-01 {
    description
      "Initial revision.";
  }

  list common_config {
    description "This is an RFS skeleton service";

    key name;
    leaf name {
      tailf:info "Unique service id";
      tailf:cli-allow-range;
      type string;
    }

    uses ncs:service-data;
    ncs:servicepoint common_config-servicepoint;

    // may replace this with other ways of refering to the devices.
    leaf-list device {
      type leafref {
        path "/ncs:devices/ncs:device/ncs:name";
      }
    }

    // replace with your own stuff here
    leaf banner_motd_yang {
      type string;
    }
    leaf banner_exec_yang {
      type string;
    }
    leaf banner_login_yang {
      type string;
    }
    leaf banner_incoming_yang {
      type string;
    }
    leaf-list dns_server_yang {
      type inet:ipv4-address;
    }
  }
}
