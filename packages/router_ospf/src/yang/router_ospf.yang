module router_ospf {

  namespace "http://example.com/router_ospf";
  prefix router_ospf;

  import ietf-inet-types {
    prefix inet;
  }
  import tailf-common {
    prefix tailf;
  }
  import tailf-ncs {
    prefix ncs;
  }

  description
    "OSPF Routing Service with MPLS LDP Auto Config";

  revision 2025-02-15 {
    description
      "Added MPLS LDP Auto Config Support.";
  }

  list router_ospf {
    description "This is an RFS skeleton service";

    key name;
    leaf name {
      tailf:info "Unique service id";
      tailf:cli-allow-range;
      type string;
    }

    uses ncs:service-data;
    ncs:servicepoint router_ospf-servicepoint;

    // may replace this with other ways of refering to the devices.
    list devices {
      key device_name;
      description "List of OSPF-enabled devices";

      leaf device_name {
        type leafref {
          path "/ncs:devices/ncs:device/ncs:name";
        }
        mandatory true;
      }

    // replace with your own stuff here
      leaf process_id {
        type uint32;
        description "OSPF process ID";
        mandatory true;
      }
      leaf router_id {
        type inet:ipv4-address;
        description "Router ID for OSPF";
        mandatory true;
      }
      leaf mpls_ldp_autoconfig {
        type boolean;
        description "Enable MPLS LDP Auto-Config for OSPF";
        default false;
      }
      list networks {
        key network_address;
        description "List of OSPF network statements-for-IOS";

        leaf network_address {
          type inet:ipv4-address;
          description "Network IP Address-for IOS";
          mandatory true;
        }

        leaf wildcard_mask {
          type inet:ipv4-address;
          description "Subnet Mask for the OSPF network-for-IOS";
          mandatory true;
        }

        leaf area {
          type uint32;
          description "OSPF Area ID";
          mandatory true;
        }
      }
      list interfaces {
        key interface_name;
        description "List of OSPF-enable interfaces-IOS-XR/XE";

        leaf interface_name {
          type string;
          description "Interface name";
          mandatory true;
        }
        leaf area {
          type uint32;
          description "OSPF Area ID for IOS-XR";
          mandatory true;
        }
      }
    }
  }
}
