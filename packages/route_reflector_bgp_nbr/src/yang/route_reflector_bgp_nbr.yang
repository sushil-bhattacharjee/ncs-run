module route_reflector_bgp_nbr {

  namespace "http://example.com/route_reflector_bgp_nbr";
  prefix route_reflector_bgp_nbr;

  import ietf-inet-types {
    prefix inet;
  }
  import tailf-common {
    prefix tailf;
  }
  import tailf-ncs {
    prefix ncs;
  }

  description
    "Service to add BGP neighbors to Route Reflector P-60";

  revision 2025-02-09 {
    description
      "Fixed device P-60, only neighbor IPs required as input.";
  }

  list route_reflector_bgp_nbr {
    key name;
    description "Input service-instance-name as key";
    uses ncs:service-data;
    ncs:servicepoint route_reflector_bgp_nbr-servicepoint;
    
    leaf name {
      tailf:info "Unique service-instance name";
      description "Service Instance Name";
      type string;
    }



    // may replace this with other ways of refering to the devices.
    list neighbors {
      key ip;
      description "List of BGP neighbors to be added";
    
      leaf ip {
        type inet:ipv4-address;
        description "BGP Neighbor IP Address";
        mandatory true;
      }
    }
  }
}
