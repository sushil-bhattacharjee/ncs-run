module cisco-iosxr-cli {
  yang-version 1.1;
  namespace "http://tail-f.com/ns/ned-id/cisco-iosxr-cli";
  prefix cisco-iosxr-cli;

  import tailf-common {
    prefix tailf;
  }

  import tailf-ncs-ned {
    prefix ned;
  }

  identity cisco-iosxr-cli {
    tailf:abstract;
    base ned:cli-ned-id;
    
  }
}
