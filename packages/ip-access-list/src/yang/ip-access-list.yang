module ip-access-list {
  namespace "http://com/example/ipaccesslist";
  prefix ip-access-list;

  import ietf-inet-types {
    prefix inet;
  }
  import protocol-base {
    prefix protocol;
  }
  organization
    "hiTech007, Inc.";  // Organization info block ends here

  contact
    "hiTech007, Inc.
     Advanced Technology Service Provider
     E-mail: Sushil.Bhattacharjee@Outlook.Com";  // Contact info block ends here

  description
    "Access Control List (ACL) YANG model.";  // Module description ends here

  revision 2025-01-19 {
    description
      "Initial revision";  // Revision block ends here
  }  // End of revision block
  typedef port-type {
    type union {
      type uint16 {
        range "0..65535";
      }
      type enumeration {
        enum "ssh" {value 22;}
        enum "telnet" {value 23;}
        enum "https" {value 443;}
        enum "http" {value 80;}
        enum "ftp" {value 21;}
        enum "pop3" {value 110;}
        enum "smtp" {value 25;}
        enum "tftp" {value 69;}
        enum "domain" {value 53;}
        enum "ntp" {value 123;}
      }
    }
  }
  identity udp {
    base protocol:protocol;
    description "The User Datagram Protocol";
  }
  identity icmp {
    base protocol:protocol;
    description "The Internet Control Message Protocol";
  }
  // Building the data with the container to include such as container, list, leaf, or leaf-list
  container acl {  // Start of 'acl' container
    description
      "Access Control Lists";  // Description of the 'acl' container

    leaf acl-description {  // Start of 'acl-description' leaf
      type string {
        length "0..64";
        pattern "[0-9a-zA-Z]*";
      }  // End of type string block for 'acl-description'
    }  // End of 'acl-description' leaf

    leaf-list maintainers {  // Start of 'maintainers' leaf-list
      type string;
      description "Name of maintainers working on the ACL";
    }  // End of 'maintainers' leaf-list

    list entry {  // Start of 'entry' list
      key "number";
      description "List of ACL entries.";

      leaf number {  // Start of 'number' leaf
        type uint16;
        description "Unique identifier for the ACL entry.";
      }  // End of 'number' leaf

      leaf action {  
        type enumeration { 
          enum permit;
          enum deny;
        }  // End of 'enumeration' type for action
      }  // End of 'action' leaf
      leaf source-ip {
        type inet:ipv4-address;
        description "Source IPv4 address";
      }
      leaf destination-ip {
        type inet:ipv4-address;
        description "Destination IPv4 address.";
      }
      leaf destination-port {
        when "../protocol != 'acl:icmp'";
        type port-type;
      }
      leaf protocol {
        type identityref {
          base protocol:protocol;
        }
        description "Protocol.";
      }
    }  // End of 'entry' list
  }  // End of 'acl' container
}  // End of module
