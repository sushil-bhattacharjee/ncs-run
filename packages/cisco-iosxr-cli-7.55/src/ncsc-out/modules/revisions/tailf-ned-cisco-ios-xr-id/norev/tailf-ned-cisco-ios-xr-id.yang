module tailf-ned-cisco-ios-xr-id {
  // Generated by yanger -t ncs
  tailf:mount-id "cisco-iosxr-cli-7.55:cisco-iosxr-cli-7.55";
  tailf:ncs-device-type "cli-ned";

  namespace "http://tail-f.com/ned/cisco-ios-xr-id";
  prefix cisco-ios-xr-id;

  import tailf-ncs-ned {
    prefix ned;
  }
  import tailf-common {
    prefix tailf;
  }
  import tailf-ncs {
    prefix ncs;
  }

  identity cisco-ios-xr {
    base ned:cli-ned-id;
  }
}
