module tailf-ned-cisco-ios-xr-stats {
  // Generated by yanger -t ncs
  tailf:mount-id "cisco-iosxr-cli-7.55:cisco-iosxr-cli-7.55";
  tailf:ncs-device-type "cli-ned";

  namespace "http://tail-f.com/ned/cisco-ios-xr-stats";
  prefix cisco-ios-xr-stats;

  import tailf-common {
    prefix tailf;
  }
  import tailf-ncs {
    prefix ncs;
  }

  augment "/ncs:devices/ncs:device/ncs:live-status" {
    list inventory {
      tailf:ncs-device-type "cli-ned";
      tailf:display-when "not(../ncs:module) or ../ncs:module[ncs:name='tailf-ned-cisco-ios-xr-stats'] or (../ncs:live-status-protocol[not(ncs:capability)]) or (../ncs:live-status-protocol/ncs:capability/ncs:module[.='tailf-ned-cisco-ios-xr-stats'])";
      tailf:info
        "show inventory";
      tailf:meta-data "ned-livestats:parser-info" {
        tailf:meta-value "{'template':'inventory.gili','show':'show inventory'}";
      }
      key "name";
      leaf name {
        type string;
      }
      leaf descr {
        type string;
      }
      leaf pid {
        type string;
      }
      leaf vid {
        type string;
      }
      leaf sn {
        type string;
      }
    }
    container cdp {
      tailf:ncs-device-type "cli-ned";
      tailf:display-when "not(../../ncs:module) or ../../ncs:module[ncs:name='tailf-ned-cisco-ios-xr-stats'] or (../../ncs:live-status-protocol[not(ncs:capability)]) or (../../ncs:live-status-protocol/ncs:capability/ncs:module[.='tailf-ned-cisco-ios-xr-stats'])";
      tailf:info
        "show cdp";
      list neighbors {
        tailf:info
          "show cdp neighbors detail";
        tailf:meta-data "ned-livestats:parser-info" {
          tailf:meta-value "{'template':'cdp_neighbors.gili','show':'show cdp neighbors detail'}";
        }
        key "local-interface";
        leaf local-interface {
          type string;
        }
        leaf device-id {
          type string;
        }
        leaf hold-time {
          type string;
        }
        leaf capability {
          type string;
        }
        leaf platform {
          type string;
        }
        leaf port-id {
          type string;
        }
      }
    }
    container lldp {
      tailf:ncs-device-type "cli-ned";
      tailf:display-when "not(../../ncs:module) or ../../ncs:module[ncs:name='tailf-ned-cisco-ios-xr-stats'] or (../../ncs:live-status-protocol[not(ncs:capability)]) or (../../ncs:live-status-protocol/ncs:capability/ncs:module[.='tailf-ned-cisco-ios-xr-stats'])";
      tailf:info
        "show lldp";
      list neighbors {
        tailf:info
          "show lldp neighbors detail";
        tailf:meta-data "ned-livestats:parser-info" {
          tailf:meta-value "{'template':'lldp_neighbors.gili','show':'show lldp neighbors detail'}";
        }
        key "local-interface";
        leaf local-interface {
          type string;
        }
        leaf parent-interface {
          type string;
        }
        leaf device-id {
          type string;
        }
        leaf time-remaining {
          type string;
        }
        leaf hold-time {
          type string;
        }
        leaf capability {
          type string;
        }
        leaf chassis-id {
          type string;
        }
        leaf port-id {
          type string;
        }
      }
    }
    container controllers {
      tailf:ncs-device-type "cli-ned";
      tailf:display-when "not(../../ncs:module) or ../../ncs:module[ncs:name='tailf-ned-cisco-ios-xr-stats'] or (../../ncs:live-status-protocol[not(ncs:capability)]) or (../../ncs:live-status-protocol/ncs:capability/ncs:module[.='tailf-ned-cisco-ios-xr-stats'])";
      tailf:info
        "Interface controller status and configuration";
      list Optics {
        tailf:info
          "OPTICS controller | short name is Op";
        tailf:meta-data "ned-livestats:parser-info" {
          tailf:meta-value "{'template':'controllers-optics.gili','show':'show run all-interfaces | include Optics','show-entry':{'cmd':'show controllers Optics %s','template':'controllers-optics-instance.gili'}}";
        }
        key "id";
        leaf id {
          type string;
        }
        container instance {
          // NCS drop tailf:cli-drop-node-name
          presence "true";
          leaf controller-state {
            type string;
          }
          container transceiver-vendor-details {
            leaf form-factor {
              type string;
            }
            leaf optics-type {
              type string;
            }
            leaf name {
              type string;
            }
            leaf oui-number {
              type string;
            }
            leaf part-number {
              type string;
            }
            leaf rev-number {
              type string;
            }
            leaf serial-number {
              type string;
            }
            leaf pid {
              type string;
            }
            leaf vid {
              type string;
            }
            leaf date-code {
              type string;
            }
          }
        }
      }
    }
    container exec {
      tailf:ncs-device-type "cli-ned";
      tailf:display-when "not(../../ncs:module) or ../../ncs:module[ncs:name='tailf-ned-cisco-ios-xr-stats'] or (../../ncs:live-status-protocol[not(ncs:capability)]) or (../../ncs:live-status-protocol/ncs:capability/ncs:module[.='tailf-ned-cisco-ios-xr-stats'])";
      tailf:info
        "Execute commands on device";
      tailf:action any {
        tailf:actionpoint ncsproxy {
          tailf:internal;
        }
        tailf:info
          "Execute any command on device";
        // NCS drop tailf:actionpoint
        input {
          leaf admin-mode {
            tailf:info
              "Set to run the action in admin mode";
            type empty;
          }
          list auto-prompts {
            tailf:info
              "One-shot auto-prompts list, used to ignore/reply on questions";
            tailf:cli-suppress-mode;
            key "question";
            leaf question {
              tailf:info
                "Device question, regular expression";
              type string {
                tailf:info
                  "WORD;;Question, regex format";
              }
            }
            leaf answer {
              tailf:info
                "Answer to device question";
              type string {
                tailf:info
                  "WORD;;Answer to device question | <exit|prompt|timeout|ignore|enter>";
              }
            }
          }
          leaf-list args {
            tailf:cli-drop-node-name;
            tailf:cli-flat-list-syntax;
            type string {
              tailf:info
                "WORD;;any \"<cmd> [option(s)]\", e.g: any \"show ppp summary\"";
            }
          }
        }
        output {
          leaf result {
            type string;
          }
        }
      }
      tailf:action any-hidden {
        tailf:actionpoint ncsproxy {
          tailf:internal;
        }
        tailf:info
          "Same as 'any' action except that nothing will be logged.";
        // NCS drop tailf:actionpoint
        input {
          leaf admin-mode {
            tailf:info
              "Set to run the action in admin mode";
            type empty;
          }
          list auto-prompts {
            tailf:info
              "One-shot auto-prompts list, used to ignore/reply on questions";
            tailf:cli-suppress-mode;
            key "question";
            leaf question {
              tailf:info
                "Device question, regular expression";
              type string {
                tailf:info
                  "WORD;;Question, regex format";
              }
            }
            leaf answer {
              tailf:info
                "Answer to device question";
              type string {
                tailf:info
                  "WORD;;Answer to device question | <exit|prompt|timeout|ignore|enter>";
              }
            }
          }
          leaf args {
            tailf:cli-drop-node-name;
            tailf:suppress-echo true;
            mandatory true;
            type string {
              tailf:info
                "WORD;;any \"<cmd> [option(s)]\", e.g: any \"show ppp summary\"";
            }
          }
        }
        output {
          leaf result {
            type string;
          }
        }
      }
      tailf:action show {
        tailf:actionpoint ncsproxy {
          tailf:internal;
        }
        tailf:info
          "Execute show commands (deprecated, use 'any')";
        // NCS drop tailf:actionpoint
        input {
          leaf-list args {
            tailf:cli-drop-node-name;
            tailf:cli-flat-list-syntax;
            type string {
              tailf:info
                "show argument(s)";
            }
          }
        }
        output {
          leaf result {
            type string;
          }
        }
      }
      tailf:action clear {
        tailf:actionpoint ncsproxy {
          tailf:internal;
        }
        tailf:info
          "Reset functions (deprecated, use 'any')";
        // NCS drop tailf:actionpoint
        input {
          leaf-list args {
            tailf:cli-drop-node-name;
            tailf:cli-flat-list-syntax;
            type string {
              tailf:info
                "clear argument(s)";
            }
          }
        }
        output {
          leaf result {
            type string;
          }
        }
      }
      tailf:action copy {
        tailf:actionpoint ncsproxy {
          tailf:internal;
        }
        tailf:info
          "Copy from one file to another (deprecated, use 'any')";
        // NCS drop tailf:actionpoint
        input {
          leaf-list args {
            tailf:cli-drop-node-name;
            tailf:cli-flat-list-syntax;
            type string {
              tailf:info
                "copy argument(s)";
            }
          }
        }
        output {
          leaf result {
            type string;
          }
        }
      }
      tailf:action reload {
        tailf:actionpoint ncsproxy {
          tailf:internal;
        }
        tailf:info
          "Halt and perform a cold restart (deprecated, use 'any')";
        // NCS drop tailf:actionpoint
        input {
          leaf-list args {
            tailf:cli-drop-node-name;
            tailf:cli-flat-list-syntax;
            type string {
              tailf:info
                "reload argument(s)";
            }
          }
        }
        output {
          leaf result {
            type string;
          }
        }
      }
      tailf:action crypto {
        tailf:actionpoint ncsproxy {
          tailf:internal;
        }
        tailf:info
          "Encryption module (deprecated, use 'any')";
        // NCS drop tailf:actionpoint
        input {
          leaf-list key {
            tailf:info
              "Long term key operations";
            tailf:cli-flat-list-syntax;
            type string {
              tailf:info
                "crypto key argument(s)";
            }
          }
        }
        output {
          leaf result {
            type string;
          }
        }
      }
    }
  }
}
