module cisco-phased-provisioning {
  yang-version 1.1;
  namespace "http://cisco.com/pkg/phased-provisioning";
  prefix cisco-pdp;

  import ietf-yang-types {
    prefix yang;
  }

  import ietf-inet-types {
    prefix inet;
  }
  import tailf-common {
    prefix tailf;
  }
  import tailf-ncs {
    prefix ncs;
  }
  import tailf-kicker {
    prefix kicker; 
  }

  organization "Tail-f Systems";

  description
    "This module defines the phased provisioning data model.

     Copyright 2023 Cisco Systems, Inc.
     All rights reserved.
     Permission is hereby granted to redistribute this file without
     modification.";

  revision 2023-09-12 {
    description
      "Added pause action under /phased-provisioning/task.
      Added retry-failures action under /phased-provisioning/task.
      Added leaf-list target-nodes as optional input for run action under /phased-provisioning/task.
      Made target leaf optional in /phased-provisioning/task.
      Added validation for /phased-provisioning/policies/policy/schedule/future/time.
      Added hidden oper leaf avg-node-exec-time under /phased-provisioning/task-status.
      Updated /phased-provisioning/policies/policy/batch/size type from int8 to uint16 and removed limit of 32.
      Updated /phased-provisioning/policies/policy/schedule/future/window/window-time type from int32 to uint32.
      Updated /phased-provisioning/task-status/allocated-error-budget type from int8 to uint8.
      Added grouping action-output to change all actions output to have result and info.
      Updated confirmation text of /phased-provisioning/task-status/purge action.
      Added pdp-name typedef for /phased-provisioning/task/name and /phased-provisioning/policies/policy/name.
      Renamed appropriately the leafs in /phased-provisioning/task-status/brief action output.
      Updated description and info statements.";
  }

  revision 2023-01-17 {
    description
      "Initial revision.";
  }

  typedef pdp-name {
    type string {
      tailf:info
        "Name can not exceed 64 characters and can only contain"
        + " alpha numeric(A-Za-z0-9), underscore(_) and hyphen(-).";
      pattern "[A-Za-z0-9_-]+" {
        error-message "Name can only contain alpha numeric(A-Za-z0-9),"
          + " underscore(_) and hyphen(-).";
      }
      length "1..64" {
        error-message "Name can not exceed 64 characters.";
      }
    }
  }

  grouping minimum-status-attributes {
    description
      "Common minimum task status attributes.";

    leaf state {
      description
        "The current state of the phased provisioning task.";
      tailf:display-column-name "State";
      type enumeration {
        enum init {
          description
            "Task is created and is waiting for change requests to schedule.";
          tailf:code-name "pdp-init";
        }
        enum in-progress {
          description
            "Execution of change requests are in-progress.";
          tailf:code-name "pdp-in-progress";
        }
        enum suspended {
          description
            "Execution suspended for issue resolution.";
          tailf:code-name "pdp-suspended";
        }
        enum completed {
          description
            "All change requests are executed successfully.";
          tailf:code-name "pdp-completed";
        }
      }
    }
    leaf reason {
      description
        "Description for the current state of the phased provisioning.";
      tailf:display-column-name "Reason";
      type string;
    }
    leaf current-error-budget {
      description
        "The error budget left after consumption.";
      tailf:display-column-name "Current Error Budget";
      type union {
        type enumeration {
          enum ignore-failures;
        }
        type int8;
      }
    }
    leaf allocated-error-budget {
      description
        "The allocated error budget for the task.";
      tailf:display-column-name "Allocated Error Budget";
      type union {
        type enumeration {
          enum ignore-failures;
        }
        type uint8;
      }
    }
    leaf last-runtime {
      description
        "The time when scheduler executed.";
      tailf:display-column-name "Last Run Time";
      type yang:date-and-time;
    }
    leaf next-runtime {
      description
        "The next scheduler execution time.";
      tailf:display-column-name "Next Run Time";
      type yang:date-and-time;
    }
    leaf schedule-task-id {
      description
        "The scheduler task used for the phased-provisioning execution.";
      tailf:display-column-name "Schedule Task Id";
      type string;
    }
    leaf avg-node-exec-time {
      tailf:hidden debug;
      description
        "Average execution time of a successful node.";
      tailf:display-column-name "Average Node Execution Time";
      type decimal64 {
        fraction-digits 6;
        range "0..max";
      }
      default 0.0;
    }
  }

  grouping action-and-test-expr-variables {
    description
      "Common list variables where both task action and self-test test-expr will be using.";
    list variable {
      // considering the action inputs are simple flat leaf structures.
      key "name";
      description
        "A list of variables bindings that will be passed on to the action. Or,
        A list of variables that will be used to replace variables in self-test test-expr.";
      leaf name {
        description
          "The name of the variable.";
        type string;
      }
      choice value-type {
        leaf value {
          description
            "The value of the variable.";
          type string;
        }
        leaf expr {
          type yang:xpath1.0 {
            tailf:info
              "An xpath 1.0 expression";
          }
          description
            "An XPath expression that will be the value of variable 'name'.
            The expression is evaluated under the instance context.
            Both expressions and path expressions are allowed,"
            + " which implies that literals must be quoted.";
        }
      }
    }
  }

  grouping action-output {
    leaf result {
      type boolean;
      mandatory true;
    }
    leaf info {
      type string;
    }
  }

  container phased-provisioning {
    description
      "Phased provisioning attempts to provide a controlled"
      + " execution of services and other actions.";
    tailf:info
      "Phased provisioning attempts to provide a controlled"
      + " execution of services and other actions.";

    leaf local-user {
      description
        "Map NCS user with sufficient permissions to read and to write into the cdb.";
      tailf:info
        "Map NCS user with sufficient permissions to read and to write into the cdb.";
      type string;
      default "admin";
    }
    list task {
      key name;
      description
        "A phased provisioning task intent.";
      tailf:info
        "A phased provisioning task intent.";
      leaf name {
        description
          "A unique identifier for task.";
        tailf:info
          "A unique identifier for task.";
        tailf:cli-allow-range;
        type pdp-name;
      }
      uses ncs:service-data;
      ncs:servicepoint "pdp-task-validation";
  
      leaf target {
        description
          "Target nodes list key path.
          The node that matches the value of this leaf should be a list.";
        tailf:info
          "Target nodes list key path.
          The node that matches the value of this leaf should be a list.";
        type tailf:node-instance-identifier {
          tailf:info
            "key path to target nodes list";
        }
      }
      leaf filter {
        when "(../target)";
        description
          "Xpath expression run against target node context to select instances.";
        tailf:info
          "Xpath expression run against target node context to select instances.";
        type yang:xpath1.0 {
          tailf:info
            "An xpath 1.0 expression";
        }
      }
      container action {
        description
          "The action to be invoked on the target instance for provisioning.";
        tailf:info
          "The action to be invoked on the target instance for provisioning.";
        leaf action-name {
          description
            "The action to be invoked on the target instance.
            Executed under node instance context, but can overwrite using absolute path.
            The action execution status is determined, if there is a leaf 'result'"
            + " (integer or boolean) in action output.
            The value of 'result' should either be int 0 or boolean true for the action to be success.
            Otherwise, the action is failed and actual failure message is determined,"
            + " if there is any one of the leaf 'info/detail/error' (string) in action output,"
            + " else, standard failure message is displayed.
            If there is no 'result' leaf in action output, the action is failed,"
            + " if there is any exception in action execution, else, it is success.";
          tailf:info
            "The action to be invoked on the target instance.
            Executed under node instance context, but can overwrite using absolute path.
            The action execution status is determined, if there is a leaf 'result'"
            + " (integer or boolean) in action output.
            The value of 'result' should either be int 0 or boolean true for the action to be success.
            Otherwise, the action is failed and actual failure message is determined,"
            + " if there is any one of the leaf 'info/detail/error' (string) in action output,"
            + " else, standard failure message is displayed.
            If there is no 'result' leaf in action output, the action is failed,"
            + " if there is any exception in action execution, else, it is success.";
          type yang:xpath1.0 {
            tailf:info
              "An xpath 1.0 expression containing the action name";
          }
          mandatory true;
        }
        uses action-and-test-expr-variables;
      }

      leaf policy {
        description
          "Policy name.";
        tailf:info
          "Policy name.";
        type leafref {
          path "../../policies/policy/name";
        }
        mandatory true;
      }
      container self-test {
        description
          "Verify and validate the execution status.";
        tailf:info
          "Verify and validate the execution status.";
  
        choice test-type {
          leaf action-name {
            description
              "A callback test action to verify the provisioning validity and status.
              Executed under node instance context, but can overwrite using absolute path.
              The output of the action must have a leaf called 'result'"
              + " (integer or boolean) which is used for validation.
              The action should return a single result int 0 or a boolean"
              + " true as output (for success scenario).
              In case of failure, the output of the action should have any one"
              + " of the leaf 'info/detail/error' (string) to get the actual"
              + " failure message or standard failure message is displayed.";
            tailf:info
              "A callback test action to verify the provisioning validity and status.
              Executed under node instance context, but can overwrite using absolute path.
              The output of the action must have a leaf called 'result'"
              + " (integer or boolean) which is used for validation.
              The action should return a single result int 0 or a boolean"
              + " true as output (for success scenario).
              In case of failure, the output of the action should have any one"
              + " of the leaf 'info/detail/error' (string) to get the actual"
              + " failure message or standard failure message is displayed.";
            type yang:xpath1.0 {
              tailf:info
                "An xpath 1.0 expression containing the action name";
            }
          }
          leaf test-expr {
            description
              "An XPath 1.0 expression to test provisioning validity and status.
              Executed under node-instance context, but can overwrite using absolute path.";
            tailf:info
              "An XPath 1.0 expression to test provisioning validity and status.
              Executed under node-instance context, but can overwrite using absolute path.";
            type yang:xpath1.0 {
              tailf:info
                "An xpath 1.0 expression";
            }
          }
        }
        uses action-and-test-expr-variables;
      }

      action run {
        description
          "Run the task and queue the target instances for phased provisioning.";
        tailf:info
          "Run the task and queue the target instances for phased provisioning.";
        tailf:actionpoint pdp-task-run;
        input {
          leaf-list target-nodes {
            when "not(../../target)";
            description
              "List of target node instances, when target and filter are not provided in task.";
            tailf:info
              "List of target node instances, when target and filter are not provided in task.";
            type string;
            min-elements 1;
          }
        }
        output {
          uses action-output;
        }
      }

      action pause {
        description
          "Pause the task to put it in suspended state.";
        tailf:info
          "Pause the task to put it in suspended state.";
        tailf:actionpoint pdp-task-pause;
        output {
          uses action-output;
        }
      }

      action resume {
        description
          "Resume a suspended task.
          It should be invoked after resolving the reason for suspension.";
        tailf:info
          "Resume a suspended task.
          It should be invoked after resolving the reason for suspension.";
        tailf:actionpoint pdp-task-resume;
        input {
          leaf reset-error-budget {
            type boolean;
          }
        }
        output {
          uses action-output;
        }
      }

      action retry-failures {
        description
          "Add failed nodes into pending queue of the task.";
        tailf:info
          "Add failed nodes into pending queue of the task.";
        tailf:actionpoint pdp-task-retry;
        input {
          leaf-list failed-nodes {
            description
              "Specific failed-nodes of the task to be added to pending.[OPTIONAL]";
            tailf:info
              "Specific failed-nodes of the task to be added to pending.[OPTIONAL]";
            type leafref {
              path "/phased-provisioning/task-status/failed-nodes/name";
            }
            must "current()/../../name=/phased-provisioning/task-status/name";
          }
        }
        output {
          uses action-output;
        }
      }

      action callback-execute-phased-provisioning {
        description
          "Internal action used by tailf:scheduler to trigger change request process.";
        tailf:info
          "Internal action used by tailf:scheduler to trigger change request process.";
        tailf:hidden full;
        tailf:actionpoint phased-provisioning-execution-handler;
      }
    }

    container policies {
      description
        "Policies to guide phased provisioning tasks.";
      tailf:info
        "Policies to guide phased provisioning tasks.";
      list policy {
        description
          "A policy to guide phased provisioning task.";
        tailf:info
          "A policy to guide phased provisioning task.";
        key name;
        leaf name {
          description
            "A unique identifier for policy.";
          tailf:info
            "A unique identifier for policy.";
          tailf:cli-allow-range;
          type pdp-name;
        }
        container schedule {
          description
            "Job schedule configuration.";
          tailf:info
            "Job schedule configuration.";
          choice schedule-type {
            case schedule-now {
              leaf immediately {
                description
                  "Schedule the job instantly.";
                tailf:info
                  "Schedule the job instantly.";
                type empty;
                mandatory true;
              }
            }
            case schedule-when {
              container future {
                leaf time {
                  description
                    "Schedule at a specific instance of time periodically.";
                  tailf:info
                    "Schedule at a specific instance of time periodically.";
                  type string {
                    tailf:info
                      "Follows Standard Vixie Crontab expression.
                      ---------- minute (0 - 59)
                      | ---------- hour (0 - 23)
                      | | ---------- day of month (1 - 31)
                      | | | ---------- month (1 - 12) | (jan - dec)
                      | | | | ---------- day of week (0 - 6) | (sun - sat)
                      | | | | |
                      * * * * *";
                  }
                  mandatory true;
                  tailf:validate "pdp-schedule-validate" {
                    tailf:dependency .;
                  }
                }
                container window {
                  leaf window-time {
                    description
                      "Execution window time.";
                    tailf:info
                      "Execution window time.";
                    type uint32 {
                      range "1..43200";
                    }
                    default 1800;
                  }
                  leaf unit {
                    description
                      "Execution window units.";
                    tailf:info
                      "Execution window units.";
                    type enumeration {
                      enum seconds {
                        tailf:code-name "pdp-seconds";
                      }
                      enum minutes {
                        tailf:code-name "pdp-minutes";
                      }
                      enum hours {
                        tailf:code-name "pdp-hours";
                      }
                      enum days {
                        tailf:code-name "pdp-days";
                      }
                    }
                    default seconds;
                  }
                }
              }
            }
          }
        }
        container batch {
          description
            "Batch processing configuration";
          tailf:info
            "Batch processing configuration";
          leaf size {
            description
              "Size of a batch processed at any given time.";
            tailf:info
              "Size of a batch processed at any given time.";
            type uint16 {
              range "1..max";
            }
            default 10;
          }
        }
        leaf error-budget {
          description
            "Total number of acceptable failures after which provisioning is stopped.
            ignore-failures: indicates ignore any failures.
            0: indicates stop provisioning on first failure.
            >0: indicates the acceptable failure rate.";
          tailf:info
            "Total number of acceptable failures after which provisioning is stopped.
            ignore-failures: indicates ignore any failures.
            0: indicates stop provisioning on first failure.
            >0: indicates the acceptable failure rate.";
          type union {
            type enumeration {
              enum ignore-failures;
            }
            type uint8;
          }
          default 0;
        }
      }
    }

    action task-change {
      tailf:hidden full;
      description
        "Internal action used by pdp-task-delete-kicker to
         delete task-status oper data when task is deleted.";
      tailf:info
        "Internal action used by pdp-task-delete-kicker to
         delete task-status oper data when task is deleted.";
      tailf:actionpoint pdp-task-change;
      input {
        uses kicker:action-input-params;
      }
    }

    action policy-change {
      tailf:hidden full;
      description
        "Internal action used by pdp-policy-update-kicker to process policy updates";
      tailf:info
        "Internal action used by pdp-policy-update-kicker to process policy updates";
      tailf:actionpoint pdp-policy-change;
      input {
        uses kicker:action-input-params;
      }
    }

    list task-status {
      description
        "Phased provisioning task status.";
      tailf:info
        "Phased provisioning task status.";
      key name;
      config false;
      tailf:cdb-oper {
        tailf:persistent true;
      }
      leaf name {
        description
          "A unique identifier for the task-status.";
        tailf:info
          "A unique identifier for the task-status.";
        tailf:display-column-name "Name";
        type string;
      }

      uses minimum-status-attributes;

      list pending-nodes {
        description
          "List of pending instance-identifiers.";
        tailf:info
          "List of pending instance-identifiers.";
        key name;
        leaf name {
          description
            "Node instance identifier.";
          tailf:info
            "Node instance identifier.";
          tailf:display-column-name "Pending Nodes";
          type string;
        }
      }
      list in-progress-nodes {
        description
          "List of in-progress instance-identifiers.";
        tailf:info
          "List of in-progress instance-identifiers.";
        key name;
        leaf name {
          description
            "Node instance identifier.";
          tailf:info
            "Node instance identifier.";
          tailf:display-column-name "In-progress Nodes";
          type string;
        }
      }
      list completed-nodes {
        description
          "List of completed instance-identifiers.";
        tailf:info
          "List of completed instance-identifiers.";
        key name;
        leaf name { 
          description
            "Node instance identifier.";
          tailf:info
            "Node instance identifier.";
          tailf:display-column-name "Completed Nodes";
          type string;
        }
      }
      list failed-nodes {
        description
          "List of failed instance-identifiers.";
        tailf:info
          "List of failed instance-identifiers.";
        key name;
        leaf name { 
          description
            "Node instance identifier.";
          tailf:info
            "Node instance identifier.";
          tailf:display-column-name "Failed Nodes";
          type string;
        }
        leaf failure-reason {
          description
            "Reason for failure of a failed instance-identifier.";
          tailf:info
            "Reason for failure of a failed instance-identifier.";
          tailf:display-column-name "Failure Reason";
          type string;
        }        
      }

      action brief {
        description
          "Task execution status in brief.";
        tailf:info
          "Task execution status in brief.";
        tailf:actionpoint pdp-task-status-short;
        output {
          uses minimum-status-attributes;
          leaf pending-nodes-count {
            description
              "Number of pending instance-identifiers.";
            tailf:info
              "Number of pending instance-identifiers.";
            type uint32;
          }
          leaf in-progress-nodes-count {
            description
              "Number of in-progress instance-identifiers.";
            tailf:info
              "Number of in-progress instance-identifiers.";
            type uint32;
          }
          leaf completed-nodes-count {
            description
              "Number of completed instance-identifiers.";
            tailf:info
              "Number of completed instance-identifiers.";
            type uint32;
          }
          leaf failed-nodes-count {
            description
              "Number of failed instance-identifiers.";
            tailf:info
              "Number of failed instance-identifiers.";
            type uint32;
          }
        }
      }

      action purge {
        description
          "Action to purge task-status operational data.";
        tailf:info
          "Action to purge task-status operational data.";
        tailf:actionpoint pdp-task-status-purge;
        output {
          uses action-output;
        }
        tailf:confirm-text
          "################################################\n"
          + "#                    Warning                   #\n"
          + "################################################\n"
          + "You are about to forcefully purge a task-status.\n"
          + "Are you sure you want to proceed?" {
          tailf:confirm-default false;
        }
      }
    }
  }
}
