module loopback {
  namespace "http://com/example/loopback";
  prefix loopback;

  import ietf-inet-types {
    prefix inet;
  }
  import tailf-ncs {
    prefix ncs;
  }
  import tailf-common {
    prefix tailf;
  }

  augment /ncs:services {
  list loopback {
    key name;

    uses ncs:service-data;
    ncs:servicepoint "loopback";

    leaf device {
      tailf:info "Router name";
      mandatory true;
      type leafref {
        path "/ncs:devices/ncs:device/ncs:name";
         }
    }
    leaf loopback-intf {
      tailf:info "Loopback Interface Number from 0 to 1199";
      mandatory true;
      type uint32 {
        range "0..1199";
      }
    }
    leaf ip-address {
    tailf:info "IP range x.x.x.x to x.x.x.x";
      mandatory true;
      type inet:ipv4-address;
      }
    leaf name {
      tailf:info "Service Instance Name";
      type string;
    }

    }
  } 
}
