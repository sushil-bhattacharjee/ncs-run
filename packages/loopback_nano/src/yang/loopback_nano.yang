module loopback_nano {
    yang-version 1.1;
    namespace "http://com/example/loopback_nano";

    prefix loopback_nano;

    import tailf-ncs {
        prefix ncs;
    }

    import ietf-inet-types {
        prefix inet;
    }

    import tailf-common {
        prefix tailf;
    }

    identity loopback {
        base ncs:plan-component-type;
    }

    identity loopback-configured {
        base ncs:plan-state;
    }

    ncs:plan-outline loopback-plan {
        description "Loopback plan";

        ncs:component-type "loopback_nano:loopback" {
            ncs:state "ncs:init";
            ncs:state "loopback_nano:loopback-configured" {
                ncs:create {
                    ncs:pre-condition {
                        ncs:monitor "/prefix-allocations[name=$SERVICE/name]/ip-prefix";
                    }
                    ncs:nano-callback;
                }
            }
            ncs:state "ncs:ready";
        }
    }

    ncs:service-behavior-tree loopback {
        description "Loopback behavior tree";
        ncs:plan-outline-ref "loopback_nano:loopback-plan";
        ncs:selector {
            ncs:create-component "'loopback_nano'" {
                ncs:component-type-ref "loopback_nano:loopback";
            }
        }
    }

    list prefix-allocations {
        key "name";
        unique "ip-prefix";

        leaf name {
            type leafref {
                path "/loopback_nano:loopback/name";
                require-instance false;
            }
        }

        leaf ip-prefix {
             type inet:ipv4-prefix;
             tailf:info "IP prefix used to configure an address loopback interface";
        }
    }

    list loopback {
        key name;

        uses ncs:service-data;
        uses ncs:nano-plan-data;
        ncs:servicepoint "loopback_nano";

        leaf name {
            tailf:cli-allow-range;
            tailf:info "Service instance name";
            type string;
        }

        leaf device {
            tailf:info "Device name";
            type leafref {
                path "/ncs:devices/ncs:device/ncs:name";
            }
        }

        leaf loopback-intf {
            tailf:info "Loopback interface number";
           type uint32;
        }

    }
}
