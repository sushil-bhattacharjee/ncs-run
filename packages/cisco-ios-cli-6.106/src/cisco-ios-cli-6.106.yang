module cisco-ios-cli-6.106 {
  yang-version 1.1;
  namespace "http://tail-f.com/ns/ned-id/cisco-ios-cli-6.106";
  prefix cisco-ios-cli-6.106;

  import cisco-ios-cli {
    prefix family;
  }

  identity cisco-ios-cli-6.106 {
    base family:cisco-ios-cli;
  }
}
