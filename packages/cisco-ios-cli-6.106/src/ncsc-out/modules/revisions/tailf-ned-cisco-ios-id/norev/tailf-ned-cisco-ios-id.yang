module tailf-ned-cisco-ios-id {
  // Generated by yanger -t ncs
  tailf:mount-id "cisco-ios-cli-6.106:cisco-ios-cli-6.106";
  tailf:ncs-device-type "cli-ned";

  namespace "urn:ios-id";
  prefix ios-id;

  import tailf-ncs-ned {
    prefix ned;
  }
  import tailf-common {
    prefix tailf;
  }
  import tailf-ncs {
    prefix ncs;
  }

  identity cisco-ios {
    base ned:cli-ned-id;
  }
}
